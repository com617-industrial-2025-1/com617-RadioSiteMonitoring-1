--
-- IRT-DAB-PASSIVERESERVE-MIB.my
-- MIB generated by MG-SOFT Visual MIB Builder Version 6.0  Build 88
-- Friday, May 04, 2007 at 17:54:08
--

	IRT-DAB-PASSIVERESERVE-MIB DEFINITIONS ::= BEGIN
 
		IMPORTS
			eventTimeStamp, eventPriority, eventCounter, mibRelease			
				FROM IRT-COMMONVARBINDS-MIB			
			dab, Input1Input2, SelectManualAuto, SelectOnOff, LocalRemote, 
			FaultOK, ReadyNotReady, ExecutedNotExecuted, PresentNotPresent, WarningOK, 
			OkNotOk, MuteOk, SFNMFN			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DisplayString, TruthValue			
				FROM SNMPv2-TC;
	
	
		-- 1.3.6.1.4.1.19831.1.1.2.3
		dabPassiveReserve MODULE-IDENTITY 
			LAST-UPDATED "200705041400Z"		-- May 04, 2007 at 14:00 GMT
			ORGANIZATION 
				"IRT for WORKING-GROUP-TC-MIB"
			CONTACT-INFO 
				"Andreas Metz
				
				Institut fuer Rundfunktechnik GmbH
				Broadcast Networks and Servers (SN)
				
				Floriansmuehlstr.60
				80939 Munich
				Germany
				
				Phone: +49 89 32399 325
				Fax: +49 89 32399 354 "
			DESCRIPTION 
				"Description.
				
				branch definition
				
				1st level
				
				events               OBJECT IDENTIFIER ::= { dabPassiveReserve 0 }
				dabPRGeneral         OBJECT IDENTIFIER ::= { dabPassiveReserve 1 }
				dabPRTransmitterA    OBJECT IDENTIFIER ::= { dabPassiveReserve 2 }
				dabPRTransmitterB    OBJECT IDENTIFIER ::= { dabPassiveReserve 3 }
				dabPREventEnable     OBJECT IDENTIFIER ::= { dabPassiveReserve 4 }
				dabPREventPriority   OBJECT IDENTIFIER ::= { dabPassiveReserve 5 }
				groups               OBJECT IDENTIFIER ::= { dabPassiveReserve 6 }
				
				2nd level
				
				dabPREventEnableGeneral        OBJECT IDENTIFIER ::= { dabPREventEnable 1 }
				dabPREventEnableTransmitterA   OBJECT IDENTIFIER ::= { dabPREventEnable 2 }
				dabPREventEnableTransmitterB   OBJECT IDENTIFIER ::= { dabPREventEnable 3 }
				
				dabPREventPriorityGeneral        OBJECT IDENTIFIER ::= { dabPREventPriority 1 }
				dabPREventPriorityTransmitterA   OBJECT IDENTIFIER ::= { dabPREventPriority 2 }
				dabPREventPriorityTransmitterB   OBJECT IDENTIFIER ::= { dabPREventPriority 3 }
				
				 end branch"
			REVISION "200705041400Z"		-- May 04, 2007 at 14:00 GMT
			DESCRIPTION 
				"change SFNMode, LocalMode (description) and Module-COMPLIANCE
				"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dab 3 }

		
	
	
--
-- Node definitions
--
	
-- dab pasive reserve events
		-- 1.3.6.1.4.1.19831.1.1.2.3.0
		dabEventsPR OBJECT IDENTIFIER ::= { dabPassiveReserve 0 }

		
		-- 1.3.6.1.4.1.19831.1.1.2.3.0.1
		dabPRInputPreselectionEvent NOTIFICATION-TYPE
			OBJECTS { sysDescr, sysName, sysLocation, eventTimeStamp, eventPriority, 
				eventCounter, dabPRInputPreselection }
			STATUS current
			DESCRIPTION 
				"Description. dabPRInputPreselection notification"
			::= { dabEventsPR 1 }

		
		-- 1.3.6.1.4.1.19831.1.1.2.3.0.2
		dabPRInputAutomaticEvent NOTIFICATION-TYPE
			OBJECTS { sysDescr, sysName, sysLocation, eventTimeStamp, eventPriority, 
				eventCounter, dabPRInputAutomatic }
			STATUS current
			DESCRIPTION 
				"Description. dabPRInputAutomatic notification"
			::= { dabEventsPR 2 }

		
		-- 1.3.6.1.4.1.19831.1.1.2.3.0.3
		dabPRPreselectionTransmitterEvent NOTIFICATION-TYPE
			OBJECTS { sysDescr, sysName, sysLocation, eventTimeStamp, eventPriority, 
				eventCounter, dabPRPreselectionTransmitter }
			STATUS current
			DESCRIPTION 
				"Description. dabPRPreselectionTransmitter notification"
			::= { dabEventsPR 3 }

		
		-- 1.3.6.1.4.1.19831.1.1.2.3.0.4
		dabPRMainTransmitterOpModeEvent NOTIFICATION-TYPE
			OBJECTS { sysDescr, sysName, sysLocation, eventTimeStamp, eventPriority, 
				eventCounter, dabPRMainTransmitterOpMode }
			STATUS current
			DESCRIPTION 
				"Description. dabPRMainTransmitterOpMode notification"
			::= { dabEventsPR 4 }

		
		-- 1.3.6.1.4.1.19831.1.1.2.3.0.5
		dabPRReserveControlEvent NOTIFICATION-TYPE
			OBJECTS { sysDescr, sysName, sysLocation, eventTimeStamp, eventPriority, 
				eventCounter, dabPRReserveControl }
			STATUS current
			DESCRIPTION 
				"Description. dabPRReserveControl notification"
			::= { dabEventsPR 5 }

		
		-- 1.3.6.1.4.1.19831.1.1.2.3.0.6
		dabPRResetFaultEvent NOTIFICATION-TYPE
			OBJECTS { sysDescr, sysName, sysLocation, eventTimeStamp, eventPriority, 
				eventCounter, dabPRResetFault }
			STATUS obsolete
			DESCRIPTION 
				"Notification is inactive!
				
				Description. dabPRResetFault notification"
			::= { dabEventsPR 6 }

		
		-- 1.3.6.1.4.1.19831.1.1.2.3.0.7
		dabPRCurrentMainTransmitterEvent NOTIFICATION-TYPE
			OBJECTS { sysDescr, sysName, sysLocation, eventTimeStamp, eventPriority, 
				eventCounter, dabPRCurrentMainTransmitter }
			STATUS current
			DESCRIPTION 
				"Description. dabPRCurrentMainTransmitter notification"
			::= { dabEventsPR 7 }

		
		-- 1.3.6.1.4.1.19831.1.1.2.3.0.8
		dabPRLocalModeEvent NOTIFICATION-TYPE
			OBJECTS { sysDescr, sysName, sysLocation, eventTimeStamp, eventPriority, 
				eventCounter, dabPRLocalMode }
			STATUS current
			DESCRIPTION 
				"Description. dabPRLocalMode notification"
			::= { dabEventsPR 8 }

		
		-- 1.3.6.1.4.1.19831.1.1.2.3.0.9
		dabPRControlUnitFaultEvent NOTIFICATION-TYPE
			OBJECTS { sysDescr, sysName, sysLocation, eventTimeStamp, eventPriority, 
				eventCounter, dabPRControlUnitFault }
			STATUS current
			DESCRIPTION 
				"Description. dabPRControlUnitFault notification"
			::= { dabEventsPR 9 }

		
		-- 1.3.6.1.4.1.19831.1.1.2.3.0.10
		dabPRSwitchOverModeEvent NOTIFICATION-TYPE
			OBJECTS { sysDescr, sysName, sysLocation, eventTimeStamp, eventPriority, 
				eventCounter, dabPRSwitchOverMode }
			STATUS current
			DESCRIPTION 
				"Description. dabPRSwitchOverMode notification"
			::= { dabEventsPR 10 }

		
		-- 1.3.6.1.4.1.19831.1.1.2.3.0.11
		dabPRSwitchOverReadyEvent NOTIFICATION-TYPE
			OBJECTS { sysDescr, sysName, sysLocation, eventTimeStamp, eventPriority, 
				eventCounter, dabPRSwitchOverReady }
			STATUS current
			DESCRIPTION 
				"Description. dabPRSwitchOverReady notification"
			::= { dabEventsPR 11 }

		
		-- 1.3.6.1.4.1.19831.1.1.2.3.0.12
		dabPRSwitchOverExecutedEvent NOTIFICATION-TYPE
			OBJECTS { sysDescr, sysName, sysLocation, eventTimeStamp, eventPriority, 
				eventCounter, dabPRSwitchOverExecuted }
			STATUS current
			DESCRIPTION 
				"Description. dabPRSwitchOverExecuted notification"
			::= { dabEventsPR 12 }

		
		-- 1.3.6.1.4.1.19831.1.1.2.3.0.13
		dabPRSwitchOverFaultEvent NOTIFICATION-TYPE
			OBJECTS { sysDescr, sysName, sysLocation, eventTimeStamp, eventPriority, 
				eventCounter, dabPRSwitchOverFault }
			STATUS current
			DESCRIPTION 
				"Description. dabPRSwitchOverFault notification"
			::= { dabEventsPR 13 }

		
		-- 1.3.6.1.4.1.19831.1.1.2.3.0.14
		dabPRTransmitterARFPresentEvent NOTIFICATION-TYPE
			OBJECTS { sysDescr, sysName, sysLocation, eventTimeStamp, eventPriority, 
				eventCounter, dabPRTransmitterARFPresent }
			STATUS current
			DESCRIPTION 
				"Description. dabPRTransmitterARFPresent notification"
			::= { dabEventsPR 14 }

		
		-- 1.3.6.1.4.1.19831.1.1.2.3.0.15
		dabPRTransmitterAFaultEvent NOTIFICATION-TYPE
			OBJECTS { sysDescr, sysName, sysLocation, eventTimeStamp, eventPriority, 
				eventCounter, dabPRTransmitterAFault }
			STATUS current
			DESCRIPTION 
				"Description. dabPRTransmitterAFault notification"
			::= { dabEventsPR 15 }

		
		-- 1.3.6.1.4.1.19831.1.1.2.3.0.16
		dabPRTransmitterAWarningEvent NOTIFICATION-TYPE
			OBJECTS { sysDescr, sysName, sysLocation, eventTimeStamp, eventPriority, 
				eventCounter, dabPRTransmitterAWarning }
			STATUS current
			DESCRIPTION 
				"Description. dabPRTransmitterAWarning notification"
			::= { dabEventsPR 16 }

		
		-- 1.3.6.1.4.1.19831.1.1.2.3.0.17
		dabPRTransmitterAInput1OKEvent NOTIFICATION-TYPE
			OBJECTS { sysDescr, sysName, sysLocation, eventTimeStamp, eventPriority, 
				eventCounter, dabPRTransmitterAInput1OK }
			STATUS current
			DESCRIPTION 
				"Description. dabPRTransmitterAInput1OK notification"
			::= { dabEventsPR 17 }

		
		-- 1.3.6.1.4.1.19831.1.1.2.3.0.18
		dabPRTransmitterAInput2OKEvent NOTIFICATION-TYPE
			OBJECTS { sysDescr, sysName, sysLocation, eventTimeStamp, eventPriority, 
				eventCounter, dabPRTransmitterAInput2OK }
			STATUS current
			DESCRIPTION 
				"Description. dabPRTransmitterAInput2OK notification"
			::= { dabEventsPR 18 }

		
		-- 1.3.6.1.4.1.19831.1.1.2.3.0.19
		dabPRTransmitterALocalModeEvent NOTIFICATION-TYPE
			OBJECTS { sysDescr, sysName, sysLocation, eventTimeStamp, eventPriority, 
				eventCounter, dabPRTransmitterALocalMode }
			STATUS current
			DESCRIPTION 
				"Description. dabPRTransmitterALocalMode notification"
			::= { dabEventsPR 19 }

		
		-- 1.3.6.1.4.1.19831.1.1.2.3.0.20
		dabPRTransmitterAActiveInputEvent NOTIFICATION-TYPE
			OBJECTS { sysDescr, sysName, sysLocation, eventTimeStamp, eventPriority, 
				eventCounter, dabPRTransmitterAActiveInput }
			STATUS current
			DESCRIPTION 
				"Description. dabPRTransmitterAActiveInput notification"
			::= { dabEventsPR 20 }

		
		-- 1.3.6.1.4.1.19831.1.1.2.3.0.21
		dabPRTransmitterASFNModeEvent NOTIFICATION-TYPE
			OBJECTS { sysDescr, sysName, sysLocation, eventTimeStamp, eventPriority, 
				eventCounter, dabPRTransmitterASFNMode }
			STATUS current
			DESCRIPTION 
				"Description. dabPRTransmitterASFNMode notification"
			::= { dabEventsPR 21 }

		
		-- 1.3.6.1.4.1.19831.1.1.2.3.0.22
		dabPRTransmitterARefFaultEvent NOTIFICATION-TYPE
			OBJECTS { sysDescr, sysName, sysLocation, eventTimeStamp, eventPriority, 
				eventCounter, dabPRTransmitterARefFault }
			STATUS current
			DESCRIPTION 
				"Description. dabPRTransmitterARefFault notification"
			::= { dabEventsPR 22 }

		
		-- 1.3.6.1.4.1.19831.1.1.2.3.0.23
		dabPRTransmitterAMuteEvent NOTIFICATION-TYPE
			OBJECTS { sysDescr, sysName, sysLocation, eventTimeStamp, eventPriority, 
				eventCounter, dabPRTransmitterAMute }
			STATUS current
			DESCRIPTION 
				"Description. dabPRTransmitterAMute notification"
			::= { dabEventsPR 23 }

		
		-- 1.3.6.1.4.1.19831.1.1.2.3.0.24
		dabPRTransmitterAWarningTimeStampEvent NOTIFICATION-TYPE
			OBJECTS { sysDescr, sysName, sysLocation, eventTimeStamp, eventPriority, 
				eventCounter, dabPRTransmitterAWarningTimeStamp }
			STATUS current
			DESCRIPTION 
				"Description. dabPRTransmitterAWarningTimeStamp notification"
			::= { dabEventsPR 24 }

		
		-- 1.3.6.1.4.1.19831.1.1.2.3.0.25
		dabPRTransmitterBRFPresentEvent NOTIFICATION-TYPE
			OBJECTS { sysDescr, sysName, sysLocation, eventTimeStamp, eventPriority, 
				eventCounter, dabPRTransmitterBRFPresent }
			STATUS current
			DESCRIPTION 
				"Description. dabPRTransmitterBRFPresent notification"
			::= { dabEventsPR 25 }

		
		-- 1.3.6.1.4.1.19831.1.1.2.3.0.26
		dabPRTransmitterBFaultEvent NOTIFICATION-TYPE
			OBJECTS { sysDescr, sysName, sysLocation, eventTimeStamp, eventPriority, 
				eventCounter, dabPRTransmitterBFault }
			STATUS current
			DESCRIPTION 
				"Description. dabPRTransmitterBFault notification"
			::= { dabEventsPR 26 }

		
		-- 1.3.6.1.4.1.19831.1.1.2.3.0.27
		dabPRTransmitterBWarningEvent NOTIFICATION-TYPE
			OBJECTS { sysDescr, sysName, sysLocation, eventTimeStamp, eventPriority, 
				eventCounter, dabPRTransmitterBWarning }
			STATUS current
			DESCRIPTION 
				"Description. dabPRTransmitterBWarning notification"
			::= { dabEventsPR 27 }

		
		-- 1.3.6.1.4.1.19831.1.1.2.3.0.28
		dabPRTransmitterBInput1OKEvent NOTIFICATION-TYPE
			OBJECTS { sysDescr, sysName, sysLocation, eventTimeStamp, eventPriority, 
				eventCounter, dabPRTransmitterBInput1OK }
			STATUS current
			DESCRIPTION 
				"Description. dabPRTransmitterBInput1OK notification"
			::= { dabEventsPR 28 }

		
		-- 1.3.6.1.4.1.19831.1.1.2.3.0.29
		dabPRTransmitterBInput2OKEvent NOTIFICATION-TYPE
			OBJECTS { sysDescr, sysName, sysLocation, eventTimeStamp, eventPriority, 
				eventCounter, dabPRTransmitterBInput2OK }
			STATUS current
			DESCRIPTION 
				"Description. dabPRTransmitterBInput2OK notification"
			::= { dabEventsPR 29 }

		
		-- 1.3.6.1.4.1.19831.1.1.2.3.0.30
		dabPRTransmitterBLocalModeEvent NOTIFICATION-TYPE
			OBJECTS { sysDescr, sysName, sysLocation, eventTimeStamp, eventPriority, 
				eventCounter, dabPRTransmitterBLocalMode }
			STATUS current
			DESCRIPTION 
				"Description. dabPRTransmitterBLocalMode notofication"
			::= { dabEventsPR 30 }

		
		-- 1.3.6.1.4.1.19831.1.1.2.3.0.31
		dabPRTransmitterBActiveInputEvent NOTIFICATION-TYPE
			OBJECTS { sysDescr, sysName, sysLocation, eventTimeStamp, eventPriority, 
				eventCounter, dabPRTransmitterBActiveInput }
			STATUS current
			DESCRIPTION 
				"Description. dabPRTransmitterBActiveInput notification"
			::= { dabEventsPR 31 }

		
		-- 1.3.6.1.4.1.19831.1.1.2.3.0.32
		dabPRTransmitterBSFNModeEvent NOTIFICATION-TYPE
			OBJECTS { sysDescr, sysName, sysLocation, eventTimeStamp, eventPriority, 
				eventCounter, dabPRTransmitterBSFNMode }
			STATUS current
			DESCRIPTION 
				"Description. dabPRTransmitterBSFNMode notification"
			::= { dabEventsPR 32 }

		
		-- 1.3.6.1.4.1.19831.1.1.2.3.0.33
		dabPRTransmitterBRefFaultEvent NOTIFICATION-TYPE
			OBJECTS { sysDescr, sysName, sysLocation, eventTimeStamp, eventPriority, 
				eventCounter, dabPRTransmitterBRefFault }
			STATUS current
			DESCRIPTION 
				"Description. dabPRTransmitterBRefFault notification"
			::= { dabEventsPR 33 }

		
		-- 1.3.6.1.4.1.19831.1.1.2.3.0.34
		dabPRTransmitterBMuteEvent NOTIFICATION-TYPE
			OBJECTS { sysDescr, sysName, sysLocation, eventTimeStamp, eventPriority, 
				eventCounter, dabPRTransmitterBMute }
			STATUS current
			DESCRIPTION 
				"Description. dabPRTransmitterBMute notification"
			::= { dabEventsPR 34 }

		
		-- 1.3.6.1.4.1.19831.1.1.2.3.0.35
		dabPRTransmitterBWarningTimeStampEvent NOTIFICATION-TYPE
			OBJECTS { sysDescr, sysName, sysLocation, eventTimeStamp, eventPriority, 
				eventCounter, dabPRTransmitterBWarningTimeStamp }
			STATUS current
			DESCRIPTION 
				"Description. dabPRTransmitterBWarningTimeStamp notification"
			::= { dabEventsPR 35 }

		
-- dab passive reserve. General
		-- 1.3.6.1.4.1.19831.1.1.2.3.1
		dabPRGeneral OBJECT IDENTIFIER ::= { dabPassiveReserve 1 }

		
		-- 1.3.6.1.4.1.19831.1.1.2.3.1.1
		dabPRInputPreselection OBJECT-TYPE
			SYNTAX Input1Input2
			MAX-ACCESS read-write
			STATUS current
			DESCRIPTION
				"Preselection input of passive reserve
				
				(0) undefined
				(1) Input 1
				(2) Input 2"
			::= { dabPRGeneral 1 }

		
		-- 1.3.6.1.4.1.19831.1.1.2.3.1.2
		dabPRInputAutomatic OBJECT-TYPE
			SYNTAX SelectManualAuto
			MAX-ACCESS read-write
			STATUS current
			DESCRIPTION
				"Passive reserve. Input selection mode manual or automatic
				
				(0) undefined
				(1) manual 
				(2) automatic"
			::= { dabPRGeneral 2 }

		
		-- 1.3.6.1.4.1.19831.1.1.2.3.1.3
		dabPRPreselectionTransmitter OBJECT-TYPE
			SYNTAX INTEGER
				{
				undefined(0),
				transmitterA(1),
				transmitterB(2)
				}
			MAX-ACCESS read-write
			STATUS current
			DESCRIPTION
				"Passive reserve. Preselection of the transmitter 
				
				"
			::= { dabPRGeneral 3 }

		
		-- 1.3.6.1.4.1.19831.1.1.2.3.1.4
		dabPRMainTransmitterOpMode OBJECT-TYPE
			SYNTAX SelectOnOff
			MAX-ACCESS read-write
			STATUS current
			DESCRIPTION
				"Passive reserve. General transmitter control 
				
				(0) undefined
				(1) ON
				(2) OFF"
			::= { dabPRGeneral 4 }

		
		-- 1.3.6.1.4.1.19831.1.1.2.3.1.5
		dabPRReserveControl OBJECT-TYPE
			SYNTAX SelectOnOff
			MAX-ACCESS read-write
			STATUS current
			DESCRIPTION
				"Passive reserve. Reserve control 
				
				(0) undefined
				(1) ON 
				(2) OFF "
			::= { dabPRGeneral 5 }

		
		-- 1.3.6.1.4.1.19831.1.1.2.3.1.6
		dabPRResetFault OBJECT-TYPE
			SYNTAX Unsigned32
			MAX-ACCESS read-write
			STATUS obsolete
			DESCRIPTION
				"Massage is inactive!
				
				Passive reserve. Reset fault: trigger for reset the sum fault
				
				<1>
				
				(1) reset sum fault
				"
			::= { dabPRGeneral 6 }

		
		-- 1.3.6.1.4.1.19831.1.1.2.3.1.7
		dabPRCurrentMainTransmitter OBJECT-TYPE
			SYNTAX INTEGER
				{
				undefined(0),
				transmitterA(1),
				transmitterB(2)
				}
			MAX-ACCESS read-only
			STATUS current
			DESCRIPTION
				"Passive reserve. Transmitter antenna mode
				
				"
			::= { dabPRGeneral 7 }

		
		-- 1.3.6.1.4.1.19831.1.1.2.3.1.8
		dabPRLocalMode OBJECT-TYPE
			SYNTAX LocalRemote
			MAX-ACCESS read-only
			STATUS current
			DESCRIPTION
				"Passive reserve. Local mode
				
				(0) undefined
				(1) local
				(2) remote"
			::= { dabPRGeneral 8 }

		
		-- 1.3.6.1.4.1.19831.1.1.2.3.1.9
		dabPRControlUnitFault OBJECT-TYPE
			SYNTAX FaultOK
			MAX-ACCESS read-only
			STATUS current
			DESCRIPTION
				"Passive reserve. State of the control unit
				
				(0) undefined
				(1) fault
				(2) ok"
			::= { dabPRGeneral 9 }

		
		-- 1.3.6.1.4.1.19831.1.1.2.3.1.10
		dabPRSwitchOverMode OBJECT-TYPE
			SYNTAX SelectManualAuto
			MAX-ACCESS read-write
			STATUS current
			DESCRIPTION
				"Passive reserve. Switch over mode manual or automatic
				
				(0) undefined
				(1) manual 
				(2) automatic"
			::= { dabPRGeneral 10 }

		
		-- 1.3.6.1.4.1.19831.1.1.2.3.1.11
		dabPRSwitchOverReady OBJECT-TYPE
			SYNTAX ReadyNotReady
			MAX-ACCESS read-only
			STATUS current
			DESCRIPTION
				"State of the passive reserve switch over unit
				
				(0) undefined
				(1) ready
				(2) not ready"
			::= { dabPRGeneral 11 }

		
		-- 1.3.6.1.4.1.19831.1.1.2.3.1.12
		dabPRSwitchOverExecuted OBJECT-TYPE
			SYNTAX ExecutedNotExecuted
			MAX-ACCESS read-only
			STATUS current
			DESCRIPTION
				"Passive reserve.Shows if the reserve switch over unit it has executed
				
				(0) undefined
				(1) executed
				(2) not executed"
			::= { dabPRGeneral 12 }

		
		-- 1.3.6.1.4.1.19831.1.1.2.3.1.13
		dabPRSwitchOverFault OBJECT-TYPE
			SYNTAX FaultOK
			MAX-ACCESS read-only
			STATUS current
			DESCRIPTION
				"Passive reserve. Fault state of the switch over unit
				
				(0) undefined
				(1) fault
				(2) ok"
			::= { dabPRGeneral 13 }

		
-- dab passive resreve. Transmitter A
		-- 1.3.6.1.4.1.19831.1.1.2.3.2
		dabPRTransmitterA OBJECT IDENTIFIER ::= { dabPassiveReserve 2 }

		
		-- 1.3.6.1.4.1.19831.1.1.2.3.2.1
		dabPRTransmitterARFPresent OBJECT-TYPE
			SYNTAX PresentNotPresent
			MAX-ACCESS read-only
			STATUS current
			DESCRIPTION
				"Passive reserve. Describes if the output power of the  transmitter A is present
				
				(0) undefined
				(1) present
				(2) not present"
			::= { dabPRTransmitterA 1 }

		
		-- 1.3.6.1.4.1.19831.1.1.2.3.2.2
		dabPRTransmitterAFault OBJECT-TYPE
			SYNTAX FaultOK
			MAX-ACCESS read-only
			STATUS current
			DESCRIPTION
				"Passive reserve. Fault state of transmitter A
				
				(0) undefined
				(1) fault
				(2) ok"
			::= { dabPRTransmitterA 2 }

		
		-- 1.3.6.1.4.1.19831.1.1.2.3.2.3
		dabPRTransmitterAWarning OBJECT-TYPE
			SYNTAX WarningOK
			MAX-ACCESS read-only
			STATUS current
			DESCRIPTION
				"Passive reserve. Warning state of transmitter A 
				
				(0) undefined
				(1) warning
				(2) ok"
			::= { dabPRTransmitterA 3 }

		
		-- 1.3.6.1.4.1.19831.1.1.2.3.2.4
		dabPRTransmitterAInput1OK OBJECT-TYPE
			SYNTAX OkNotOk
			MAX-ACCESS read-only
			STATUS current
			DESCRIPTION
				"Passive reserve. Describes if the input signal at the input 1 of transmitter A  is ok
				
				(0) undefined
				(1) signal ok
				(2) signal is not ok "
			::= { dabPRTransmitterA 4 }

		
		-- 1.3.6.1.4.1.19831.1.1.2.3.2.5
		dabPRTransmitterAInput2OK OBJECT-TYPE
			SYNTAX OkNotOk
			MAX-ACCESS read-only
			STATUS current
			DESCRIPTION
				"Passive reserve. Describes if the input signal at the input 2 of transmitter A  is ok
				
				(0) undefined
				(1) signal ok
				(2) signal is not ok "
			::= { dabPRTransmitterA 5 }

		
		-- 1.3.6.1.4.1.19831.1.1.2.3.2.6
		dabPRTransmitterALocalMode OBJECT-TYPE
			SYNTAX LocalRemote
			MAX-ACCESS read-only
			STATUS current
			DESCRIPTION
				"Passive reserve. Local mode of transmitter A
				
				(0) undefined
				(1) local
				(2) remote"
			::= { dabPRTransmitterA 6 }

		
		-- 1.3.6.1.4.1.19831.1.1.2.3.2.7
		dabPRTransmitterAActiveInput OBJECT-TYPE
			SYNTAX INTEGER
				{
				undefined(0),
				input1(1),
				input2(2),
				seamless(3),
				hmHierarchicalModulation(4)
				}
			MAX-ACCESS read-only
			STATUS current
			DESCRIPTION
				"Passive Resereve. Active Input of the transmitter A 
				
				"
			::= { dabPRTransmitterA 7 }

		
		-- 1.3.6.1.4.1.19831.1.1.2.3.2.8
		dabPRTransmitterASFNMode OBJECT-TYPE
			SYNTAX SFNMFN
			MAX-ACCESS read-only
			STATUS current
			DESCRIPTION
				"Passive reserve. SFN mode of transmitter A
				
				(0) undefined
				(1) SFN
				(2) MFN"
			::= { dabPRTransmitterA 8 }

		
		-- 1.3.6.1.4.1.19831.1.1.2.3.2.9
		dabPRTransmitterARefFault OBJECT-TYPE
			SYNTAX FaultOK
			MAX-ACCESS read-only
			STATUS current
			DESCRIPTION
				"Passive reserve. Fault state of the GPS input or the reference frequency of transmitter A
				
				(0) undefined
				(1) fault
				(2) ok"
			::= { dabPRTransmitterA 9 }

		
		-- 1.3.6.1.4.1.19831.1.1.2.3.2.10
		dabPRTransmitterAMute OBJECT-TYPE
			SYNTAX MuteOk
			MAX-ACCESS read-only
			STATUS current
			DESCRIPTION
				"Passive reserve. Mute state of transmitter A
				
				(0) undefined
				(1) mute
				(2) ok"
			::= { dabPRTransmitterA 10 }

		
		-- 1.3.6.1.4.1.19831.1.1.2.3.2.11
		dabPRTransmitterAWarningTimeStamp OBJECT-TYPE
			SYNTAX WarningOK
			MAX-ACCESS read-only
			STATUS current
			DESCRIPTION
				"Passive reserve. Time stamp warning of transmitter A
				
				(0) undefined
				(1) warning
				(2) ok"
			::= { dabPRTransmitterA 11 }

		
-- dab passive reserve. Transmitter B
		-- 1.3.6.1.4.1.19831.1.1.2.3.3
		dabPRTransmitterB OBJECT IDENTIFIER ::= { dabPassiveReserve 3 }

		
		-- 1.3.6.1.4.1.19831.1.1.2.3.3.1
		dabPRTransmitterBRFPresent OBJECT-TYPE
			SYNTAX PresentNotPresent
			MAX-ACCESS read-only
			STATUS current
			DESCRIPTION
				"Passive reserve. Describes if the output power of the  transmitter B is present
				
				(0) undefined
				(1) present
				(2) not present"
			::= { dabPRTransmitterB 1 }

		
		-- 1.3.6.1.4.1.19831.1.1.2.3.3.2
		dabPRTransmitterBFault OBJECT-TYPE
			SYNTAX FaultOK
			MAX-ACCESS read-only
			STATUS current
			DESCRIPTION
				"Passive reserve. Fault state of transmitters B
				
				(0) undefined
				(1) fault
				(2) ok"
			::= { dabPRTransmitterB 2 }

		
		-- 1.3.6.1.4.1.19831.1.1.2.3.3.3
		dabPRTransmitterBWarning OBJECT-TYPE
			SYNTAX WarningOK
			MAX-ACCESS read-only
			STATUS current
			DESCRIPTION
				"Passive reserve. Warning state of transmiters B 
				
				(0) undefined
				(1) warning
				(2) ok"
			::= { dabPRTransmitterB 3 }

		
		-- 1.3.6.1.4.1.19831.1.1.2.3.3.4
		dabPRTransmitterBInput1OK OBJECT-TYPE
			SYNTAX OkNotOk
			MAX-ACCESS read-only
			STATUS current
			DESCRIPTION
				"Passive reserve. Describes if the input signal at the input 1 of transmitterB is ok
				
				(0) undefined
				(1) signal ok
				(2) signal is not ok "
			::= { dabPRTransmitterB 4 }

		
		-- 1.3.6.1.4.1.19831.1.1.2.3.3.5
		dabPRTransmitterBInput2OK OBJECT-TYPE
			SYNTAX OkNotOk
			MAX-ACCESS read-only
			STATUS current
			DESCRIPTION
				"Passive reserve. Describes if the input signal at the input 2 of transmitter B is ok
				
				(0) undefined
				(1) signal ok
				(2) signal is not ok "
			::= { dabPRTransmitterB 5 }

		
		-- 1.3.6.1.4.1.19831.1.1.2.3.3.6
		dabPRTransmitterBLocalMode OBJECT-TYPE
			SYNTAX LocalRemote
			MAX-ACCESS read-only
			STATUS current
			DESCRIPTION
				"Passive reserve. Local mode of transmitter B
				
				(0) undefined
				(1) local
				(2) remote"
			::= { dabPRTransmitterB 6 }

		
		-- 1.3.6.1.4.1.19831.1.1.2.3.3.7
		dabPRTransmitterBActiveInput OBJECT-TYPE
			SYNTAX INTEGER
				{
				undefined(0),
				input1(1),
				input2(2),
				seamless(3),
				hmHierarchicalModulation(4)
				}
			MAX-ACCESS read-only
			STATUS current
			DESCRIPTION
				"Passive reserve. Active input of the transmitter B 
				
				"
			::= { dabPRTransmitterB 7 }

		
		-- 1.3.6.1.4.1.19831.1.1.2.3.3.8
		dabPRTransmitterBSFNMode OBJECT-TYPE
			SYNTAX SFNMFN
			MAX-ACCESS read-only
			STATUS current
			DESCRIPTION
				"Passive reserve. SFN mode of transmitter B
				
				(0) undefined
				(1) SFN
				(2) MFN"
			::= { dabPRTransmitterB 8 }

		
		-- 1.3.6.1.4.1.19831.1.1.2.3.3.9
		dabPRTransmitterBRefFault OBJECT-TYPE
			SYNTAX FaultOK
			MAX-ACCESS read-only
			STATUS current
			DESCRIPTION
				"Passive reserve. Fault state of the GPS input or the reference frequency of transmitter B
				
				(0) undefined
				(1) fault
				(2) ok"
			::= { dabPRTransmitterB 9 }

		
		-- 1.3.6.1.4.1.19831.1.1.2.3.3.10
		dabPRTransmitterBMute OBJECT-TYPE
			SYNTAX MuteOk
			MAX-ACCESS read-only
			STATUS current
			DESCRIPTION
				"Passive reserve. Mute state of transmitter B
				
				(1) mute
				(2) ok"
			::= { dabPRTransmitterB 10 }

		
		-- 1.3.6.1.4.1.19831.1.1.2.3.3.11
		dabPRTransmitterBWarningTimeStamp OBJECT-TYPE
			SYNTAX WarningOK
			MAX-ACCESS read-only
			STATUS current
			DESCRIPTION
				"Passive reserve. Time stamp warning state of transmiter B 
				
				
				(0) undefined
				(1) warning
				(2) ok"
			::= { dabPRTransmitterB 11 }

		
-- dab passive reserve. Switch for event
		-- 1.3.6.1.4.1.19831.1.1.2.3.4
		dabPREventEnable OBJECT IDENTIFIER ::= { dabPassiveReserve 4 }

		
-- dab passive reserve general: switch for Event
		-- 1.3.6.1.4.1.19831.1.1.2.3.4.1
		dabPREventEnableGeneral OBJECT IDENTIFIER ::= { dabPREventEnable 1 }

		
		-- 1.3.6.1.4.1.19831.1.1.2.3.4.1.1
		dabPRInputPreselectionEnable OBJECT-TYPE
			SYNTAX TruthValue
			MAX-ACCESS read-write
			STATUS current
			DESCRIPTION
				"Description.Enable/Disable switch for dabARInputPreselection event"
			::= { dabPREventEnableGeneral 1 }

		
		-- 1.3.6.1.4.1.19831.1.1.2.3.4.1.2
		dabPRInputAutomaticEnable OBJECT-TYPE
			SYNTAX TruthValue
			MAX-ACCESS read-write
			STATUS current
			DESCRIPTION
				"Description.Enable/Disable switch for dabARInputAutomatic event"
			::= { dabPREventEnableGeneral 2 }

		
		-- 1.3.6.1.4.1.19831.1.1.2.3.4.1.3
		dabPRPreselectionTransmitterEnable OBJECT-TYPE
			SYNTAX TruthValue
			MAX-ACCESS read-write
			STATUS current
			DESCRIPTION
				"Description.Enable/Disable switch for dabPRPreselectionTransmitter event"
			::= { dabPREventEnableGeneral 3 }

		
		-- 1.3.6.1.4.1.19831.1.1.2.3.4.1.4
		dabPRMainTransmitterOpModeEnable OBJECT-TYPE
			SYNTAX TruthValue
			MAX-ACCESS read-write
			STATUS current
			DESCRIPTION
				"Description.Enable/Disable switch for dabPRMainTransmitterOpMode event"
			::= { dabPREventEnableGeneral 4 }

		
		-- 1.3.6.1.4.1.19831.1.1.2.3.4.1.5
		dabPRReserveControlEnable OBJECT-TYPE
			SYNTAX TruthValue
			MAX-ACCESS read-write
			STATUS current
			DESCRIPTION
				"Description.Enable/Disable switch for dabPRReserveControl event"
			::= { dabPREventEnableGeneral 5 }

		
		-- 1.3.6.1.4.1.19831.1.1.2.3.4.1.6
		dabPRResetFaultEnable OBJECT-TYPE
			SYNTAX TruthValue
			MAX-ACCESS read-write
			STATUS obsolete
			DESCRIPTION
				"Massage is inactive!
				
				Description.Enable/Disable switch for dabPRResetFault event"
			::= { dabPREventEnableGeneral 6 }

		
		-- 1.3.6.1.4.1.19831.1.1.2.3.4.1.7
		dabPRCurrentMainTransmitterEnable OBJECT-TYPE
			SYNTAX TruthValue
			MAX-ACCESS read-write
			STATUS current
			DESCRIPTION
				"Description.Enable/Disable switch for dabPRCurrentMainTransmitter event"
			::= { dabPREventEnableGeneral 7 }

		
		-- 1.3.6.1.4.1.19831.1.1.2.3.4.1.8
		dabPRLocalModeEnable OBJECT-TYPE
			SYNTAX TruthValue
			MAX-ACCESS read-write
			STATUS current
			DESCRIPTION
				"Description.Enable/Disable switch for dabPRLocalMode event"
			::= { dabPREventEnableGeneral 8 }

		
		-- 1.3.6.1.4.1.19831.1.1.2.3.4.1.9
		dabPRControlUnitFaultEnable OBJECT-TYPE
			SYNTAX TruthValue
			MAX-ACCESS read-write
			STATUS current
			DESCRIPTION
				"Description.Enable/Disable switch for dabPRControlUnitFault event"
			::= { dabPREventEnableGeneral 9 }

		
		-- 1.3.6.1.4.1.19831.1.1.2.3.4.1.10
		dabPRSwitchOverModeEnable OBJECT-TYPE
			SYNTAX TruthValue
			MAX-ACCESS read-write
			STATUS current
			DESCRIPTION
				"Description.Enable/Disable switch for dabPRSwitchOverMode event"
			::= { dabPREventEnableGeneral 10 }

		
		-- 1.3.6.1.4.1.19831.1.1.2.3.4.1.11
		dabPRSwitchOverReadyEnable OBJECT-TYPE
			SYNTAX TruthValue
			MAX-ACCESS read-write
			STATUS current
			DESCRIPTION
				"Description.Enable/Disable switch for dabPRSwitchOverReady event"
			::= { dabPREventEnableGeneral 11 }

		
		-- 1.3.6.1.4.1.19831.1.1.2.3.4.1.12
		dabPRSwitchOverExecutedEnable OBJECT-TYPE
			SYNTAX TruthValue
			MAX-ACCESS read-write
			STATUS current
			DESCRIPTION
				"Description.Enable/Disable switch for dabPRSwitchOverExecuted event"
			::= { dabPREventEnableGeneral 12 }

		
		-- 1.3.6.1.4.1.19831.1.1.2.3.4.1.13
		dabPRSwitchOverFaultEnable OBJECT-TYPE
			SYNTAX TruthValue
			MAX-ACCESS read-write
			STATUS current
			DESCRIPTION
				"Description.Enable/Disable switch for dabPRSwitchOverFault event"
			::= { dabPREventEnableGeneral 13 }

		
-- dab passive reserve transmitter A: switch for Event
		-- 1.3.6.1.4.1.19831.1.1.2.3.4.2
		dabPREventEnableTransmitterA OBJECT IDENTIFIER ::= { dabPREventEnable 2 }

		
		-- 1.3.6.1.4.1.19831.1.1.2.3.4.2.1
		dabPRTransmitterARFPresentEnable OBJECT-TYPE
			SYNTAX TruthValue
			MAX-ACCESS read-write
			STATUS current
			DESCRIPTION
				"Description.Enable/Disable switch for dabPRTransmitterARFPresent event"
			::= { dabPREventEnableTransmitterA 1 }

		
		-- 1.3.6.1.4.1.19831.1.1.2.3.4.2.2
		dabPRTransmitterAFaultEnable OBJECT-TYPE
			SYNTAX TruthValue
			MAX-ACCESS read-write
			STATUS current
			DESCRIPTION
				"Description.Enable/Disable switch for dabPRTransmitterAFault event"
			::= { dabPREventEnableTransmitterA 2 }

		
		-- 1.3.6.1.4.1.19831.1.1.2.3.4.2.3
		dabPRTransmitterAWarningEnable OBJECT-TYPE
			SYNTAX TruthValue
			MAX-ACCESS read-write
			STATUS current
			DESCRIPTION
				"Description.Enable/Disable switch for dabPRTransmitterAWarning event"
			::= { dabPREventEnableTransmitterA 3 }

		
		-- 1.3.6.1.4.1.19831.1.1.2.3.4.2.4
		dabPRTransmitterAInput1OKEnable OBJECT-TYPE
			SYNTAX TruthValue
			MAX-ACCESS read-write
			STATUS current
			DESCRIPTION
				"Description.Enable/Disable switch for dabPRTransmitterAInput1OK event"
			::= { dabPREventEnableTransmitterA 4 }

		
		-- 1.3.6.1.4.1.19831.1.1.2.3.4.2.5
		dabPRTransmitterAInput2OKEnable OBJECT-TYPE
			SYNTAX TruthValue
			MAX-ACCESS read-write
			STATUS current
			DESCRIPTION
				"Description.Enable/Disable switch for dabPRTransmitterAInput2OK event"
			::= { dabPREventEnableTransmitterA 5 }

		
		-- 1.3.6.1.4.1.19831.1.1.2.3.4.2.6
		dabPRTransmitterALocalModeEnable OBJECT-TYPE
			SYNTAX TruthValue
			MAX-ACCESS read-write
			STATUS current
			DESCRIPTION
				"Description.Enable/Disable switch for dabPRTransmitterALocalMode event"
			::= { dabPREventEnableTransmitterA 6 }

		
		-- 1.3.6.1.4.1.19831.1.1.2.3.4.2.7
		dabPRTransmitterAActiveInputEnable OBJECT-TYPE
			SYNTAX TruthValue
			MAX-ACCESS read-write
			STATUS current
			DESCRIPTION
				"Description.Enable/Disable switch for dabPRTransmitterAActiveInput event"
			::= { dabPREventEnableTransmitterA 7 }

		
		-- 1.3.6.1.4.1.19831.1.1.2.3.4.2.8
		dabPRTransmitterASFNModeEnable OBJECT-TYPE
			SYNTAX TruthValue
			MAX-ACCESS read-write
			STATUS current
			DESCRIPTION
				"Description.Enable/Disable switch for dabPRTransmitterASFNMode event"
			::= { dabPREventEnableTransmitterA 8 }

		
		-- 1.3.6.1.4.1.19831.1.1.2.3.4.2.9
		dabPRTransmitterARefFaultEnable OBJECT-TYPE
			SYNTAX TruthValue
			MAX-ACCESS read-write
			STATUS current
			DESCRIPTION
				"Description.Enable/Disable switch for dabPRTransmitterARefFault event"
			::= { dabPREventEnableTransmitterA 9 }

		
		-- 1.3.6.1.4.1.19831.1.1.2.3.4.2.10
		dabPRTransmitterAMuteEnable OBJECT-TYPE
			SYNTAX TruthValue
			MAX-ACCESS read-write
			STATUS current
			DESCRIPTION
				"Description.Enable/Disable switch for dabPRTransmitterAMute event"
			::= { dabPREventEnableTransmitterA 10 }

		
		-- 1.3.6.1.4.1.19831.1.1.2.3.4.2.11
		dabPRTransmitterAWarningTimeStampEnable OBJECT-TYPE
			SYNTAX TruthValue
			MAX-ACCESS read-write
			STATUS current
			DESCRIPTION
				"Description.Enable/Disable switch for dabPRTransmitterAWarningTimeStamp event"
			::= { dabPREventEnableTransmitterA 11 }

		
-- dab passive reserve transmitter B: switch for Event
		-- 1.3.6.1.4.1.19831.1.1.2.3.4.3
		dabPREventEnableTransmitterB OBJECT IDENTIFIER ::= { dabPREventEnable 3 }

		
		-- 1.3.6.1.4.1.19831.1.1.2.3.4.3.1
		dabPRTransmitterBRFPresentEnable OBJECT-TYPE
			SYNTAX TruthValue
			MAX-ACCESS read-write
			STATUS current
			DESCRIPTION
				"Description.Enable/Disable switch for dabPRTransmitterBRFPresent event"
			::= { dabPREventEnableTransmitterB 1 }

		
		-- 1.3.6.1.4.1.19831.1.1.2.3.4.3.2
		dabPRTransmitterBFaultEnable OBJECT-TYPE
			SYNTAX TruthValue
			MAX-ACCESS read-write
			STATUS current
			DESCRIPTION
				"Description.Enable/Disable switch for dabPRAmplifierBFault event"
			::= { dabPREventEnableTransmitterB 2 }

		
		-- 1.3.6.1.4.1.19831.1.1.2.3.4.3.3
		dabPRTransmitterBWarningEnable OBJECT-TYPE
			SYNTAX TruthValue
			MAX-ACCESS read-write
			STATUS current
			DESCRIPTION
				"Description.Enable/Disable switch for dabPRAmplifierBWarning event"
			::= { dabPREventEnableTransmitterB 3 }

		
		-- 1.3.6.1.4.1.19831.1.1.2.3.4.3.4
		dabPRTransmitterBInput1OKEnable OBJECT-TYPE
			SYNTAX TruthValue
			MAX-ACCESS read-write
			STATUS current
			DESCRIPTION
				"Description.Enable/Disable switch for dabPRTransmitterBInput1OK event"
			::= { dabPREventEnableTransmitterB 4 }

		
		-- 1.3.6.1.4.1.19831.1.1.2.3.4.3.5
		dabPRTransmitterBInput2OKEnable OBJECT-TYPE
			SYNTAX TruthValue
			MAX-ACCESS read-write
			STATUS current
			DESCRIPTION
				"Description.Enable/Disable switch for dabPRTransmitterBInput2OK event"
			::= { dabPREventEnableTransmitterB 5 }

		
		-- 1.3.6.1.4.1.19831.1.1.2.3.4.3.6
		dabPRTransmitterBLocalModeEnable OBJECT-TYPE
			SYNTAX TruthValue
			MAX-ACCESS read-write
			STATUS current
			DESCRIPTION
				"Description.Enable/Disable switch for dabPRTransmitterBLocalMode event"
			::= { dabPREventEnableTransmitterB 6 }

		
		-- 1.3.6.1.4.1.19831.1.1.2.3.4.3.7
		dabPRTransmitterBActiveInputEnable OBJECT-TYPE
			SYNTAX TruthValue
			MAX-ACCESS read-write
			STATUS current
			DESCRIPTION
				"Description.Enable/Disable switch for dabPRSwitchOverFault event"
			::= { dabPREventEnableTransmitterB 7 }

		
		-- 1.3.6.1.4.1.19831.1.1.2.3.4.3.8
		dabPRTransmitterBSFNModeEnable OBJECT-TYPE
			SYNTAX TruthValue
			MAX-ACCESS read-write
			STATUS current
			DESCRIPTION
				"Description.Enable/Disable switch for dabPRTransmitterBSFNMode event
				"
			::= { dabPREventEnableTransmitterB 8 }

		
		-- 1.3.6.1.4.1.19831.1.1.2.3.4.3.9
		dabPRTransmitterBRefFaultEnable OBJECT-TYPE
			SYNTAX TruthValue
			MAX-ACCESS read-write
			STATUS current
			DESCRIPTION
				"Description.Enable/Disable switch for dabPRTransmitterBRefFault event"
			::= { dabPREventEnableTransmitterB 9 }

		
		-- 1.3.6.1.4.1.19831.1.1.2.3.4.3.10
		dabPRTransmitterBMuteEnable OBJECT-TYPE
			SYNTAX TruthValue
			MAX-ACCESS read-write
			STATUS current
			DESCRIPTION
				"Description.Enable/Disable switch for dabPRTransmitterBMute event"
			::= { dabPREventEnableTransmitterB 10 }

		
		-- 1.3.6.1.4.1.19831.1.1.2.3.4.3.11
		dabPRTransmitterBWarningTimeStampEnable OBJECT-TYPE
			SYNTAX TruthValue
			MAX-ACCESS read-write
			STATUS current
			DESCRIPTION
				"Description.Enable/Disable switch for dabPRTransmitterBWarningTimeStamp event"
			::= { dabPREventEnableTransmitterB 11 }

		
-- dab passive reserve event priority
		-- 1.3.6.1.4.1.19831.1.1.2.3.5
		dabPREventPriority OBJECT IDENTIFIER ::= { dabPassiveReserve 5 }

		
-- dab passive reserve event priority general
		-- 1.3.6.1.4.1.19831.1.1.2.3.5.1
		dabPREventPriorityGeneral OBJECT IDENTIFIER ::= { dabPREventPriority 1 }

		
		-- 1.3.6.1.4.1.19831.1.1.2.3.5.1.1
		dabPRInputPreselectionPriority OBJECT-TYPE
			SYNTAX Unsigned32
			MAX-ACCESS read-write
			STATUS current
			DESCRIPTION
				"Description.Priority for dabPPRInputPreselection event"
			::= { dabPREventPriorityGeneral 1 }

		
		-- 1.3.6.1.4.1.19831.1.1.2.3.5.1.2
		dabPRInputAutomaticPriority OBJECT-TYPE
			SYNTAX Unsigned32
			MAX-ACCESS read-write
			STATUS current
			DESCRIPTION
				"Description.Priority for dabPRInputAutomatic event"
			::= { dabPREventPriorityGeneral 2 }

		
		-- 1.3.6.1.4.1.19831.1.1.2.3.5.1.3
		dabPRPreselectionTransmitterPriority OBJECT-TYPE
			SYNTAX Unsigned32
			MAX-ACCESS read-write
			STATUS current
			DESCRIPTION
				"Description.Priority for dabPRPreselectionTransmitter event"
			::= { dabPREventPriorityGeneral 3 }

		
		-- 1.3.6.1.4.1.19831.1.1.2.3.5.1.4
		dabPRMainTransmitterOpModePriority OBJECT-TYPE
			SYNTAX Unsigned32
			MAX-ACCESS read-write
			STATUS current
			DESCRIPTION
				"Description.Priority for dabPRMainTransmitterOpMode event"
			::= { dabPREventPriorityGeneral 4 }

		
		-- 1.3.6.1.4.1.19831.1.1.2.3.5.1.5
		dabPRReserveControlPriority OBJECT-TYPE
			SYNTAX Unsigned32
			MAX-ACCESS read-write
			STATUS current
			DESCRIPTION
				"Description.Priority for dabPRReserveControl event"
			::= { dabPREventPriorityGeneral 5 }

		
		-- 1.3.6.1.4.1.19831.1.1.2.3.5.1.6
		dabPRResetFaultPriority OBJECT-TYPE
			SYNTAX Unsigned32
			MAX-ACCESS read-write
			STATUS obsolete
			DESCRIPTION
				"Massage is inactive!
				
				Description.Priority for dabPRResetFault event"
			::= { dabPREventPriorityGeneral 6 }

		
		-- 1.3.6.1.4.1.19831.1.1.2.3.5.1.7
		dabPRCurrentMainTransmitterPriority OBJECT-TYPE
			SYNTAX Unsigned32
			MAX-ACCESS read-write
			STATUS current
			DESCRIPTION
				"Description.Priority for dabPRCurrentMainTransmitter event"
			::= { dabPREventPriorityGeneral 7 }

		
		-- 1.3.6.1.4.1.19831.1.1.2.3.5.1.8
		dabPRLocalModePriority OBJECT-TYPE
			SYNTAX Unsigned32
			MAX-ACCESS read-write
			STATUS current
			DESCRIPTION
				"Description.Priority for dabPRLocalMode event"
			::= { dabPREventPriorityGeneral 8 }

		
		-- 1.3.6.1.4.1.19831.1.1.2.3.5.1.9
		dabPRControlUnitFaultPriority OBJECT-TYPE
			SYNTAX Unsigned32
			MAX-ACCESS read-write
			STATUS current
			DESCRIPTION
				"Description.Priority for dabPRControlUnitFault event"
			::= { dabPREventPriorityGeneral 9 }

		
		-- 1.3.6.1.4.1.19831.1.1.2.3.5.1.10
		dabPRSwitchOverModePriority OBJECT-TYPE
			SYNTAX Unsigned32
			MAX-ACCESS read-write
			STATUS current
			DESCRIPTION
				"Description.Priority for dabPRSwitchOverMode event"
			::= { dabPREventPriorityGeneral 10 }

		
		-- 1.3.6.1.4.1.19831.1.1.2.3.5.1.11
		dabPRSwitchOverReadyPriority OBJECT-TYPE
			SYNTAX Unsigned32
			MAX-ACCESS read-write
			STATUS current
			DESCRIPTION
				"Description.Priority for dabPRSwitchOverReady event"
			::= { dabPREventPriorityGeneral 11 }

		
		-- 1.3.6.1.4.1.19831.1.1.2.3.5.1.12
		dabPRSwitchOverExecutedPriority OBJECT-TYPE
			SYNTAX Unsigned32
			MAX-ACCESS read-write
			STATUS current
			DESCRIPTION
				"Description.Priority for dabPRSwitchOverExecuted event"
			::= { dabPREventPriorityGeneral 12 }

		
		-- 1.3.6.1.4.1.19831.1.1.2.3.5.1.13
		dabPRSwitchOverFaultPriority OBJECT-TYPE
			SYNTAX Unsigned32
			MAX-ACCESS read-write
			STATUS current
			DESCRIPTION
				"Description.Priority for dabPRSwitchOverFault event"
			::= { dabPREventPriorityGeneral 13 }

		
-- dab passive reserve event priority transmitter A
		-- 1.3.6.1.4.1.19831.1.1.2.3.5.2
		dabPREventPriorityTransmitteA OBJECT IDENTIFIER ::= { dabPREventPriority 2 }

		
		-- 1.3.6.1.4.1.19831.1.1.2.3.5.2.1
		dabPRTransmitterARFPresentPriority OBJECT-TYPE
			SYNTAX Unsigned32
			MAX-ACCESS read-write
			STATUS current
			DESCRIPTION
				"Description.Priority for dabPRTransmitterARFPresent event"
			::= { dabPREventPriorityTransmitteA 1 }

		
		-- 1.3.6.1.4.1.19831.1.1.2.3.5.2.2
		dabPRTransmitterAFaultPriority OBJECT-TYPE
			SYNTAX Unsigned32
			MAX-ACCESS read-write
			STATUS current
			DESCRIPTION
				"Description.Priority for dabPRTransmitterAFault event"
			::= { dabPREventPriorityTransmitteA 2 }

		
		-- 1.3.6.1.4.1.19831.1.1.2.3.5.2.3
		dabPRTransmitterAWarningPriority OBJECT-TYPE
			SYNTAX Unsigned32
			MAX-ACCESS read-write
			STATUS current
			DESCRIPTION
				"Description.Priority for dabPRTransmitterAWarning event"
			::= { dabPREventPriorityTransmitteA 3 }

		
		-- 1.3.6.1.4.1.19831.1.1.2.3.5.2.4
		dabPRTransmitterAInput1OKPriority OBJECT-TYPE
			SYNTAX Unsigned32
			MAX-ACCESS read-write
			STATUS current
			DESCRIPTION
				"Description.Priority for dabPRTransmitterAInput1OK event"
			::= { dabPREventPriorityTransmitteA 4 }

		
		-- 1.3.6.1.4.1.19831.1.1.2.3.5.2.5
		dabPRTransmitterAInput2OKPriority OBJECT-TYPE
			SYNTAX Unsigned32
			MAX-ACCESS read-write
			STATUS current
			DESCRIPTION
				"Description.Priority for dabPRTransmitterAInput2OK event"
			::= { dabPREventPriorityTransmitteA 5 }

		
		-- 1.3.6.1.4.1.19831.1.1.2.3.5.2.6
		dabPRTransmitterALocalModePriority OBJECT-TYPE
			SYNTAX Unsigned32
			MAX-ACCESS read-write
			STATUS current
			DESCRIPTION
				"Description.Priority for dabPRTransmitterALocalMode event"
			::= { dabPREventPriorityTransmitteA 6 }

		
		-- 1.3.6.1.4.1.19831.1.1.2.3.5.2.7
		dabPRTransmitterAActiveInputPriority OBJECT-TYPE
			SYNTAX Unsigned32
			MAX-ACCESS read-write
			STATUS current
			DESCRIPTION
				"Description.Priority for dabPRTransmitterAActiveInput event"
			::= { dabPREventPriorityTransmitteA 7 }

		
		-- 1.3.6.1.4.1.19831.1.1.2.3.5.2.8
		dabPRTransmitterASFNModePriority OBJECT-TYPE
			SYNTAX Unsigned32
			MAX-ACCESS read-write
			STATUS current
			DESCRIPTION
				"Description.Priority for dabPRTransmitterASFNMode event"
			::= { dabPREventPriorityTransmitteA 8 }

		
		-- 1.3.6.1.4.1.19831.1.1.2.3.5.2.9
		dabPRTransmitterARefFaultPriority OBJECT-TYPE
			SYNTAX Unsigned32
			MAX-ACCESS read-write
			STATUS current
			DESCRIPTION
				"Description.Priority for dabPRTransmitterARefFault event"
			::= { dabPREventPriorityTransmitteA 9 }

		
		-- 1.3.6.1.4.1.19831.1.1.2.3.5.2.10
		dabPRTransmitterAMutePriority OBJECT-TYPE
			SYNTAX Unsigned32
			MAX-ACCESS read-write
			STATUS current
			DESCRIPTION
				"Description.Priority for dabPRTransmitterAMute event"
			::= { dabPREventPriorityTransmitteA 10 }

		
		-- 1.3.6.1.4.1.19831.1.1.2.3.5.2.11
		dabPRTransmitterAWarningTimeStampPriority OBJECT-TYPE
			SYNTAX Unsigned32
			MAX-ACCESS read-write
			STATUS current
			DESCRIPTION
				"Description.Priority for dabPRTransmitterAWarningTimeStamp event"
			::= { dabPREventPriorityTransmitteA 11 }

		
-- dab passive reserve event priority transmitter B 
		-- 1.3.6.1.4.1.19831.1.1.2.3.5.3
		dabPREventPriorityTransmitterB OBJECT IDENTIFIER ::= { dabPREventPriority 3 }

		
		-- 1.3.6.1.4.1.19831.1.1.2.3.5.3.1
		dabPRTransmitterBRFPresentPriority OBJECT-TYPE
			SYNTAX Unsigned32
			MAX-ACCESS read-write
			STATUS current
			DESCRIPTION
				"Description.Priority for dabPRTransmitterBRFPresent event"
			::= { dabPREventPriorityTransmitterB 1 }

		
		-- 1.3.6.1.4.1.19831.1.1.2.3.5.3.2
		dabPRTransmitterBFaultPriority OBJECT-TYPE
			SYNTAX Unsigned32
			MAX-ACCESS read-write
			STATUS current
			DESCRIPTION
				"Description.Priority for dabPRAmplifierBFault event"
			::= { dabPREventPriorityTransmitterB 2 }

		
		-- 1.3.6.1.4.1.19831.1.1.2.3.5.3.3
		dabPRTransmitterBWarningPriority OBJECT-TYPE
			SYNTAX Unsigned32
			MAX-ACCESS read-write
			STATUS current
			DESCRIPTION
				"Description.Priority for dabPRAmplifierBWarning event"
			::= { dabPREventPriorityTransmitterB 3 }

		
		-- 1.3.6.1.4.1.19831.1.1.2.3.5.3.4
		dabPRTransmitterBInput1OKPriority OBJECT-TYPE
			SYNTAX Unsigned32
			MAX-ACCESS read-write
			STATUS current
			DESCRIPTION
				"Description.Priority for dabPRTransmitterBInput1OK event"
			::= { dabPREventPriorityTransmitterB 4 }

		
		-- 1.3.6.1.4.1.19831.1.1.2.3.5.3.5
		dabPRTransmitterBInput2OKPriority OBJECT-TYPE
			SYNTAX Unsigned32
			MAX-ACCESS read-write
			STATUS current
			DESCRIPTION
				"Description.Priority for dabPRTransmitterBInput2OK event"
			::= { dabPREventPriorityTransmitterB 5 }

		
		-- 1.3.6.1.4.1.19831.1.1.2.3.5.3.6
		dabPRTransmitterBLocalModePriority OBJECT-TYPE
			SYNTAX Unsigned32
			MAX-ACCESS read-write
			STATUS current
			DESCRIPTION
				"Description.Priority for dabPRTransmitterBLocalMode event"
			::= { dabPREventPriorityTransmitterB 6 }

		
		-- 1.3.6.1.4.1.19831.1.1.2.3.5.3.7
		dabPRTransmitterBActiveInputPriority OBJECT-TYPE
			SYNTAX Unsigned32
			MAX-ACCESS read-write
			STATUS current
			DESCRIPTION
				"Description.Priority for dabPRTransmitterBActiveInput event"
			::= { dabPREventPriorityTransmitterB 7 }

		
		-- 1.3.6.1.4.1.19831.1.1.2.3.5.3.8
		dabPRTransmitterBSFNModePriority OBJECT-TYPE
			SYNTAX Unsigned32
			MAX-ACCESS read-write
			STATUS current
			DESCRIPTION
				"Description.Priority for dabPRTransmitterBSFNMode event"
			::= { dabPREventPriorityTransmitterB 8 }

		
		-- 1.3.6.1.4.1.19831.1.1.2.3.5.3.9
		dabPRTransmitterBRefFaultPriority OBJECT-TYPE
			SYNTAX Unsigned32
			MAX-ACCESS read-write
			STATUS current
			DESCRIPTION
				"Description.Priority for dabPRTransmitterBRefFault event"
			::= { dabPREventPriorityTransmitterB 9 }

		
		-- 1.3.6.1.4.1.19831.1.1.2.3.5.3.10
		dabPRTransmitterBMutePriority OBJECT-TYPE
			SYNTAX Unsigned32
			MAX-ACCESS read-write
			STATUS current
			DESCRIPTION
				"Description.Priority for dabPRTransmitterBMute event"
			::= { dabPREventPriorityTransmitterB 10 }

		
		-- 1.3.6.1.4.1.19831.1.1.2.3.5.3.11
		dabPRTransmitterBWarningTimeStampPriority OBJECT-TYPE
			SYNTAX Unsigned32
			MAX-ACCESS read-write
			STATUS current
			DESCRIPTION
				"Description.Priority for dabPRTransmitterBWarningTimeStamp event"
			::= { dabPREventPriorityTransmitterB 11 }

		
		-- 1.3.6.1.4.1.19831.1.1.2.3.6
		groupsPR OBJECT IDENTIFIER ::= { dabPassiveReserve 6 }

		
		-- 1.3.6.1.4.1.19831.1.1.2.3.6.1
		obgectGroupPR OBJECT-GROUP
			OBJECTS { dabPRInputPreselection, dabPRInputAutomatic, dabPRPreselectionTransmitter, dabPRMainTransmitterOpMode, dabPRReserveControl, 
				dabPRCurrentMainTransmitter, dabPRLocalMode, dabPRControlUnitFault, dabPRSwitchOverMode, dabPRSwitchOverReady, 
				dabPRSwitchOverExecuted, dabPRSwitchOverFault, dabPRTransmitterARFPresent, dabPRTransmitterAFault, dabPRTransmitterAWarning, 
				dabPRTransmitterAInput1OK, dabPRTransmitterAInput2OK, dabPRTransmitterALocalMode, dabPRTransmitterAActiveInput, dabPRTransmitterASFNMode, 
				dabPRTransmitterARefFault, dabPRTransmitterAMute, dabPRTransmitterAWarningTimeStamp, dabPRTransmitterBRFPresent, dabPRTransmitterBFault, 
				dabPRTransmitterBWarning, dabPRTransmitterBInput1OK, dabPRTransmitterBInput2OK, dabPRTransmitterBLocalMode, dabPRTransmitterBActiveInput, 
				dabPRTransmitterBSFNMode, dabPRTransmitterBRefFault, dabPRTransmitterBMute, dabPRTransmitterBWarningTimeStamp, dabPRInputPreselectionEnable, 
				dabPRInputAutomaticEnable, dabPRPreselectionTransmitterEnable, dabPRMainTransmitterOpModeEnable, dabPRReserveControlEnable, dabPRCurrentMainTransmitterEnable, 
				dabPRLocalModeEnable, dabPRControlUnitFaultEnable, dabPRSwitchOverModeEnable, dabPRSwitchOverReadyEnable, dabPRSwitchOverExecutedEnable, 
				dabPRTransmitterARFPresentEnable, dabPRTransmitterAFaultEnable, dabPRTransmitterAWarningEnable, dabPRTransmitterAInput1OKEnable, dabPRTransmitterAInput2OKEnable, 
				dabPRTransmitterALocalModeEnable, dabPRTransmitterAActiveInputEnable, dabPRTransmitterASFNModeEnable, dabPRTransmitterARefFaultEnable, dabPRTransmitterAMuteEnable, 
				dabPRTransmitterAWarningTimeStampEnable, dabPRTransmitterBRFPresentEnable, dabPRTransmitterBFaultEnable, dabPRTransmitterBWarningEnable, dabPRTransmitterBInput1OKEnable, 
				dabPRTransmitterBInput2OKEnable, dabPRTransmitterBLocalModeEnable, dabPRTransmitterBActiveInputEnable, dabPRTransmitterBSFNModeEnable, dabPRTransmitterBRefFaultEnable, 
				dabPRTransmitterBMuteEnable, dabPRTransmitterBWarningTimeStampEnable, dabPRInputPreselectionPriority, dabPRInputAutomaticPriority, dabPRPreselectionTransmitterPriority, 
				dabPRMainTransmitterOpModePriority, dabPRReserveControlPriority, dabPRCurrentMainTransmitterPriority, dabPRLocalModePriority, dabPRControlUnitFaultPriority, 
				dabPRSwitchOverModePriority, dabPRSwitchOverReadyPriority, dabPRSwitchOverExecutedPriority, dabPRSwitchOverFaultPriority, dabPRTransmitterARFPresentPriority, 
				dabPRTransmitterAFaultPriority, dabPRTransmitterAWarningPriority, dabPRTransmitterAInput1OKPriority, dabPRTransmitterAInput2OKPriority, dabPRTransmitterALocalModePriority, 
				dabPRTransmitterAActiveInputPriority, dabPRTransmitterASFNModePriority, dabPRTransmitterARefFaultPriority, dabPRTransmitterAMutePriority, dabPRTransmitterAWarningTimeStampPriority, 
				dabPRTransmitterBRFPresentPriority, dabPRTransmitterBFaultPriority, dabPRTransmitterBWarningPriority, dabPRTransmitterBInput1OKPriority, dabPRTransmitterBInput2OKPriority, 
				dabPRTransmitterBLocalModePriority, dabPRTransmitterBActiveInputPriority, dabPRTransmitterBSFNModePriority, dabPRTransmitterBRefFaultPriority, dabPRTransmitterBMutePriority, 
				dabPRTransmitterBWarningTimeStampPriority, dabPRSwitchOverFaultEnable }
			STATUS current
			DESCRIPTION 
				"Description. objects"
			::= { groupsPR 1 }

		
		-- 1.3.6.1.4.1.19831.1.1.2.3.6.2
		eventGrpupPR NOTIFICATION-GROUP
			NOTIFICATIONS { dabPRInputPreselectionEvent, dabPRInputAutomaticEvent, dabPRPreselectionTransmitterEvent, dabPRMainTransmitterOpModeEvent, dabPRReserveControlEvent, 
				dabPRCurrentMainTransmitterEvent, dabPRLocalModeEvent, dabPRControlUnitFaultEvent, dabPRSwitchOverModeEvent, dabPRSwitchOverReadyEvent, 
				dabPRSwitchOverExecutedEvent, dabPRSwitchOverFaultEvent, dabPRTransmitterARFPresentEvent, dabPRTransmitterAFaultEvent, dabPRTransmitterAWarningEvent, 
				dabPRTransmitterAInput1OKEvent, dabPRTransmitterAInput2OKEvent, dabPRTransmitterALocalModeEvent, dabPRTransmitterAActiveInputEvent, dabPRTransmitterASFNModeEvent, 
				dabPRTransmitterARefFaultEvent, dabPRTransmitterAMuteEvent, dabPRTransmitterAWarningTimeStampEvent, dabPRTransmitterBRFPresentEvent, dabPRTransmitterBFaultEvent, 
				dabPRTransmitterBWarningEvent, dabPRTransmitterBInput1OKEvent, dabPRTransmitterBInput2OKEvent, dabPRTransmitterBLocalModeEvent, dabPRTransmitterBActiveInputEvent, 
				dabPRTransmitterBSFNModeEvent, dabPRTransmitterBRefFaultEvent, dabPRTransmitterBMuteEvent, dabPRTransmitterBWarningTimeStampEvent }
			STATUS current
			DESCRIPTION 
				"Description. events"
			::= { groupsPR 2 }

		
		-- 1.3.6.1.4.1.19831.1.1.2.3.6.3
		objectCroupPRobsolete OBJECT-GROUP
			OBJECTS { dabPRResetFault, dabPRResetFaultEnable, dabPRResetFaultPriority }
			STATUS obsolete
			DESCRIPTION 
				"Description.Inactive objects"
			::= { groupsPR 3 }

		
		-- 1.3.6.1.4.1.19831.1.1.2.3.6.4
		eventGroupPRobsolete NOTIFICATION-GROUP
			NOTIFICATIONS { dabPRResetFaultEvent }
			STATUS obsolete
			DESCRIPTION 
				"Description. Inactive ivets"
			::= { groupsPR 4 }

		
		-- 1.3.6.1.4.1.19831.1.1.2.3.6.5
		compliancePR OBJECT IDENTIFIER ::= { groupsPR 5 }

		
		-- 1.3.6.1.4.1.19831.1.1.2.3.6.5.1
		dabPassiveReserveCompliance MODULE-COMPLIANCE
			STATUS current
			DESCRIPTION 
				"Compliance Statement"
			MODULE -- this module
				MANDATORY-GROUPS { obgectGroupPR, eventGrpupPR }
			::= { compliancePR 1 }

		
	
	END

--
-- IRT-DAB-PASSIVERESERVE-MIB.my
--
