--
-- IRT-FM-PASSIVERESERVE-MIB.my
-- MIB generated by MG-SOFT Visual MIB Builder Version 6.0  Build 88
-- Friday, May 04, 2007 at 18:46:08
--

	IRT-FM-PASSIVERESERVE-MIB DEFINITIONS ::= BEGIN
 
		IMPORTS
			eventTimeStamp, eventPriority, eventCounter, mibRelease			
				FROM IRT-COMMONVARBINDS-MIB			
			fm, SelectOnOff, LocalRemote, FaultOK, SelectManualAuto, 
			ReadyNotReady, ExecutedNotExecuted, PresentNotPresent, WarningOK			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			TruthValue			
				FROM SNMPv2-TC;
	
	
		-- 1.3.6.1.4.1.19831.1.1.3.3
		fmPassiveReserve MODULE-IDENTITY 
			LAST-UPDATED "200705041400Z"		-- May 04, 2007 at 14:00 GMT
			ORGANIZATION 
				"IRT for WORKING-GRPOUP-TC-MIB"
			CONTACT-INFO 
				"Contact-info.
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				
				branch definition
				
				1st level
				
				events               OBJECT IDENTIFIER ::= { dvbPassiveReserve 0 }
				dvbPRGeneral         OBJECT IDENTIFIER ::= { dvbPassiveReserve 1 }
				dvbPRTransmitterA    OBJECT IDENTIFIER ::= { dvbPassiveReserve 2 }
				dvbPRTransmitterB    OBJECT IDENTIFIER ::= { dvbPassiveReserve 3 }
				dvbPREventEnable     OBJECT IDENTIFIER ::= { dvbPassiveReserve 4 }
				dvbPREventPriority   OBJECT IDENTIFIER ::= { dvbPassiveReserve 5 }
				groups               OBJECT IDENTIFIER ::= { dvbPassiveReserve 6 }
				
				2nd level
				
				dvbPREventEnableGeneral        OBJECT IDENTIFIER ::= { dvbPREventEnable 1 }
				dvbPREventEnableTransmitterA   OBJECT IDENTIFIER ::= { dvbPREventEnable 2 }
				dvbPREventEnableTransmitterB   OBJECT IDENTIFIER ::= { dvbPREventEnable 3 }
				
				dvbPREventPriorityGeneral        OBJECT IDENTIFIER ::= { dvbPREventPriority 1 }
				dvbPREventPriorityTransmitterA   OBJECT IDENTIFIER ::= { dvbPREventPriority 2 }
				dvbPREventPriorityTransmitterB   OBJECT IDENTIFIER ::= { dvbPREventPriority 3 }
				
				 end branch"
			REVISION "200705041400Z"		-- May 04, 2007 at 14:00 GMT
			DESCRIPTION 
				"change LocalMode (description) and Module-COMPLIANCE"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { fm 3 }

		
	
	
--
-- Node definitions
--
	
-- fm events passive reserve
		-- 1.3.6.1.4.1.19831.1.1.3.3.0
		fmEventsPR OBJECT IDENTIFIER ::= { fmPassiveReserve 0 }

		
		-- 1.3.6.1.4.1.19831.1.1.3.3.0.1
		fmPRPreselectionTransmitterEvent NOTIFICATION-TYPE
			OBJECTS { sysDescr, sysName, fmPRPreselectionTransmitter, sysLocation, eventTimeStamp, 
				eventCounter, eventPriority }
			STATUS current
			DESCRIPTION 
				"Description. fmPRPreselectionTransmitter notification"
			::= { fmEventsPR 1 }

		
		-- 1.3.6.1.4.1.19831.1.1.3.3.0.2
		fmPRMainTransmitterOpModeEvent NOTIFICATION-TYPE
			OBJECTS { sysDescr, sysName, sysLocation, eventTimeStamp, eventPriority, 
				eventCounter, fmPRMainTransmitterOpMode }
			STATUS current
			DESCRIPTION 
				"Description. fmPRMainTransmitterOpMode notification"
			::= { fmEventsPR 2 }

		
		-- 1.3.6.1.4.1.19831.1.1.3.3.0.3
		fmPRReserveControlEvent NOTIFICATION-TYPE
			OBJECTS { sysDescr, sysName, sysLocation, eventTimeStamp, eventPriority, 
				eventCounter, fmPRReserveControl }
			STATUS current
			DESCRIPTION 
				"Description.fmPRReserveControl notification"
			::= { fmEventsPR 3 }

		
		-- 1.3.6.1.4.1.19831.1.1.3.3.0.4
		fmPRCurrentMainTransmitterEvent NOTIFICATION-TYPE
			OBJECTS { sysDescr, sysName, sysLocation, eventTimeStamp, eventPriority, 
				eventCounter, fmPRCurrentMainTransmitter }
			STATUS current
			DESCRIPTION 
				"Description. fmPRCurrentMainTransmitter notification"
			::= { fmEventsPR 4 }

		
		-- 1.3.6.1.4.1.19831.1.1.3.3.0.5
		fmPRLocalModeEvent NOTIFICATION-TYPE
			OBJECTS { sysDescr, sysName, sysLocation, eventTimeStamp, eventPriority, 
				eventCounter, fmPRLocalMode }
			STATUS current
			DESCRIPTION 
				"Description. fmPRLocalMode notification"
			::= { fmEventsPR 5 }

		
		-- 1.3.6.1.4.1.19831.1.1.3.3.0.6
		fmPRControlUnitFaultEvent NOTIFICATION-TYPE
			OBJECTS { sysDescr, sysName, sysLocation, eventTimeStamp, eventPriority, 
				eventCounter, fmPRControlUnitFault }
			STATUS current
			DESCRIPTION 
				"Description. fmPRControlUnitFault notification"
			::= { fmEventsPR 6 }

		
		-- 1.3.6.1.4.1.19831.1.1.3.3.0.7
		fmPRSwitchOverModeEvent NOTIFICATION-TYPE
			OBJECTS { sysDescr, sysName, sysLocation, eventTimeStamp, eventPriority, 
				eventCounter, fmPRSwitchOverMode }
			STATUS current
			DESCRIPTION 
				"Description. fmPRSwitchOverMode notification"
			::= { fmEventsPR 7 }

		
		-- 1.3.6.1.4.1.19831.1.1.3.3.0.8
		fmPRSwitchOverReadyEvent NOTIFICATION-TYPE
			OBJECTS { sysDescr, sysName, sysLocation, eventTimeStamp, eventPriority, 
				eventCounter, fmPRSwitchOverReady }
			STATUS current
			DESCRIPTION 
				"Description. fmPRSwitchOverReady notification"
			::= { fmEventsPR 8 }

		
		-- 1.3.6.1.4.1.19831.1.1.3.3.0.9
		fmPRSwitchOverExecutedEvent NOTIFICATION-TYPE
			OBJECTS { sysDescr, sysName, sysLocation, eventTimeStamp, eventPriority, 
				eventCounter, fmPRSwitchOverExecuted }
			STATUS current
			DESCRIPTION 
				"Description. fmPRSwitchOverExecuted notification"
			::= { fmEventsPR 9 }

		
		-- 1.3.6.1.4.1.19831.1.1.3.3.0.10
		fmPRSwitchOverFaultEvent NOTIFICATION-TYPE
			OBJECTS { sysDescr, sysName, sysLocation, eventTimeStamp, eventPriority, 
				eventCounter, fmPRSwitchOverFault }
			STATUS current
			DESCRIPTION 
				"Description. fmPRSwitchOverFault notification"
			::= { fmEventsPR 10 }

		
		-- 1.3.6.1.4.1.19831.1.1.3.3.0.11
		fmPRTransmitterARFPresentEvent NOTIFICATION-TYPE
			OBJECTS { sysDescr, sysName, sysLocation, eventTimeStamp, eventPriority, 
				eventCounter, fmPRTransmitterARFPresent }
			STATUS current
			DESCRIPTION 
				"Description. fmPRTransmitterARFPresent notification"
			::= { fmEventsPR 11 }

		
		-- 1.3.6.1.4.1.19831.1.1.3.3.0.12
		fmPRTransmitterALocalModeEvent NOTIFICATION-TYPE
			OBJECTS { sysDescr, sysName, sysLocation, eventTimeStamp, eventPriority, 
				eventCounter, fmPRTransmitterALocalMode }
			STATUS current
			DESCRIPTION 
				"Description. fmPRTransmitterALocalMode notification"
			::= { fmEventsPR 12 }

		
		-- 1.3.6.1.4.1.19831.1.1.3.3.0.13
		fmPRTransmitterAFaultEvent NOTIFICATION-TYPE
			OBJECTS { sysDescr, sysName, sysLocation, eventTimeStamp, eventPriority, 
				eventCounter, fmPRTransmitterAFault }
			STATUS current
			DESCRIPTION 
				"Description. fmPRTransmitterAFault notification"
			::= { fmEventsPR 13 }

		
		-- 1.3.6.1.4.1.19831.1.1.3.3.0.14
		fmPRTransmitterAWarningEvent NOTIFICATION-TYPE
			OBJECTS { sysDescr, sysName, sysLocation, eventTimeStamp, eventPriority, 
				eventCounter, fmPRTransmitterAWarning }
			STATUS current
			DESCRIPTION 
				"Description. fmPRTransmitterAWarning notification"
			::= { fmEventsPR 14 }

		
		-- 1.3.6.1.4.1.19831.1.1.3.3.0.15
		fmPRTransmitterBRFPresentEvent NOTIFICATION-TYPE
			OBJECTS { sysDescr, sysName, sysLocation, eventTimeStamp, eventPriority, 
				eventCounter, fmPRTransmitterBRFPresent }
			STATUS current
			DESCRIPTION 
				"Description. fmPRTransmitterBRFPresent notification"
			::= { fmEventsPR 15 }

		
		-- 1.3.6.1.4.1.19831.1.1.3.3.0.16
		fmPRTransmitterBLocalModeEvent NOTIFICATION-TYPE
			OBJECTS { sysDescr, sysName, sysLocation, eventTimeStamp, eventPriority, 
				eventCounter, fmPRTransmitterBLocalMode }
			STATUS current
			DESCRIPTION 
				"Description. fmPRTransmitterBLocalMode notofication"
			::= { fmEventsPR 16 }

		
		-- 1.3.6.1.4.1.19831.1.1.3.3.0.17
		fmPRTransmitterBFaultEvent NOTIFICATION-TYPE
			OBJECTS { sysDescr, sysName, sysLocation, eventTimeStamp, eventPriority, 
				eventCounter, fmPRTransmitterBFault }
			STATUS current
			DESCRIPTION 
				"Description. fmPRTransmitterBFault notification"
			::= { fmEventsPR 17 }

		
		-- 1.3.6.1.4.1.19831.1.1.3.3.0.18
		fmPRTransmitterBWarningEvent NOTIFICATION-TYPE
			OBJECTS { sysDescr, sysName, sysLocation, eventTimeStamp, eventPriority, 
				eventCounter, fmPRTransmitterBWarning }
			STATUS current
			DESCRIPTION 
				"Description. fmPRTransmitterBWarning notification"
			::= { fmEventsPR 18 }

		
-- fm passiver reserve general
		-- 1.3.6.1.4.1.19831.1.1.3.3.1
		fmPRGeneral OBJECT IDENTIFIER ::= { fmPassiveReserve 1 }

		
		-- 1.3.6.1.4.1.19831.1.1.3.3.1.1
		fmPRPreselectionTransmitter OBJECT-TYPE
			SYNTAX INTEGER
				{
				undefined(0),
				transmitterA(1),
				transmitterB(2)
				}
			MAX-ACCESS read-write
			STATUS current
			DESCRIPTION
				"Passive reserve. Preselection of the transmitter 
				
				"
			::= { fmPRGeneral 1 }

		
		-- 1.3.6.1.4.1.19831.1.1.3.3.1.2
		fmPRMainTransmitterOpMode OBJECT-TYPE
			SYNTAX SelectOnOff
			MAX-ACCESS read-write
			STATUS current
			DESCRIPTION
				"Passive reserve. General transmitter control 
				
				(0) undefined
				(1) ON
				(2) OFF"
			::= { fmPRGeneral 2 }

		
		-- 1.3.6.1.4.1.19831.1.1.3.3.1.3
		fmPRReserveControl OBJECT-TYPE
			SYNTAX SelectOnOff
			MAX-ACCESS read-write
			STATUS current
			DESCRIPTION
				"Passive reserve. Reserve control 
				
				(0) undefined
				(1) ON 
				(2) OFF "
			::= { fmPRGeneral 3 }

		
		-- 1.3.6.1.4.1.19831.1.1.3.3.1.4
		fmPRCurrentMainTransmitter OBJECT-TYPE
			SYNTAX INTEGER
				{
				undefined(0),
				transmitterA(1),
				transmitterB(2)
				}
			MAX-ACCESS read-only
			STATUS current
			DESCRIPTION
				"Passive reserve. Transmitter antenna mode
				
				"
			::= { fmPRGeneral 4 }

		
		-- 1.3.6.1.4.1.19831.1.1.3.3.1.5
		fmPRLocalMode OBJECT-TYPE
			SYNTAX LocalRemote
			MAX-ACCESS read-only
			STATUS current
			DESCRIPTION
				"Passive reserve. Local mode
				
				(0) undefined
				(1) local
				(2) remote"
			::= { fmPRGeneral 5 }

		
		-- 1.3.6.1.4.1.19831.1.1.3.3.1.6
		fmPRControlUnitFault OBJECT-TYPE
			SYNTAX FaultOK
			MAX-ACCESS read-only
			STATUS current
			DESCRIPTION
				"Passive reserve. State of the control unit
				
				(0) undefined
				(1) fault
				(2) ok"
			::= { fmPRGeneral 6 }

		
		-- 1.3.6.1.4.1.19831.1.1.3.3.1.7
		fmPRSwitchOverMode OBJECT-TYPE
			SYNTAX SelectManualAuto
			MAX-ACCESS read-write
			STATUS current
			DESCRIPTION
				"Passive reserve. Switch over mode manual or automatic
				
				(0) undefined
				(1) manual 
				(2) automatic"
			::= { fmPRGeneral 7 }

		
		-- 1.3.6.1.4.1.19831.1.1.3.3.1.8
		fmPRSwitchOverReady OBJECT-TYPE
			SYNTAX ReadyNotReady
			MAX-ACCESS read-only
			STATUS current
			DESCRIPTION
				"State of the passive reserve switch over unit
				
				(0) undefined
				(1) ready
				(2) not ready"
			::= { fmPRGeneral 8 }

		
		-- 1.3.6.1.4.1.19831.1.1.3.3.1.9
		fmPRSwitchOverExecuted OBJECT-TYPE
			SYNTAX ExecutedNotExecuted
			MAX-ACCESS read-only
			STATUS current
			DESCRIPTION
				"Passive reserve.Shows if the reserve switch over unit it has executed
				
				(0) undefined
				(1) executed
				(2) not executed"
			::= { fmPRGeneral 9 }

		
		-- 1.3.6.1.4.1.19831.1.1.3.3.1.10
		fmPRSwitchOverFault OBJECT-TYPE
			SYNTAX FaultOK
			MAX-ACCESS read-only
			STATUS current
			DESCRIPTION
				"Passive reserve. Fault state of the switch over unit
				
				(0) undefined
				(1) faulty
				(2) ok"
			::= { fmPRGeneral 10 }

		
-- fm passive reserve transmitter A
		-- 1.3.6.1.4.1.19831.1.1.3.3.2
		fmPRTransmitterA OBJECT IDENTIFIER ::= { fmPassiveReserve 2 }

		
		-- 1.3.6.1.4.1.19831.1.1.3.3.2.1
		fmPRTransmitterARFPresent OBJECT-TYPE
			SYNTAX PresentNotPresent
			MAX-ACCESS read-only
			STATUS current
			DESCRIPTION
				"Passive reserve. Describes if the output power of the  transmitter A is present
				
				(0) undefined
				(1) present
				(2) not present"
			::= { fmPRTransmitterA 1 }

		
		-- 1.3.6.1.4.1.19831.1.1.3.3.2.2
		fmPRTransmitterALocalMode OBJECT-TYPE
			SYNTAX LocalRemote
			MAX-ACCESS read-only
			STATUS current
			DESCRIPTION
				"Passive reserve. Local mode of transmitter A
				
				(0) undefined
				(1) local
				(2) remote"
			::= { fmPRTransmitterA 2 }

		
		-- 1.3.6.1.4.1.19831.1.1.3.3.2.3
		fmPRTransmitterAFault OBJECT-TYPE
			SYNTAX FaultOK
			MAX-ACCESS read-only
			STATUS current
			DESCRIPTION
				"Passive reserve. Fault state of transmitter A
				
				(0) undefined
				(1) fault
				(2) ok"
			::= { fmPRTransmitterA 3 }

		
		-- 1.3.6.1.4.1.19831.1.1.3.3.2.4
		fmPRTransmitterAWarning OBJECT-TYPE
			SYNTAX WarningOK
			MAX-ACCESS read-only
			STATUS current
			DESCRIPTION
				"Passive reserve. Warning state of transmitter A 
				
				(0) undefined
				(1) warning
				(2) ok"
			::= { fmPRTransmitterA 4 }

		
-- fm passive reserve transmitter B
		-- 1.3.6.1.4.1.19831.1.1.3.3.3
		fmPRTransmitterB OBJECT IDENTIFIER ::= { fmPassiveReserve 3 }

		
		-- 1.3.6.1.4.1.19831.1.1.3.3.3.1
		fmPRTransmitterBRFPresent OBJECT-TYPE
			SYNTAX PresentNotPresent
			MAX-ACCESS read-only
			STATUS current
			DESCRIPTION
				"Passive reserve. Describes if the output power of the  transmitter B is present
				
				(0) undefined
				(1) present
				(2) not present"
			::= { fmPRTransmitterB 1 }

		
		-- 1.3.6.1.4.1.19831.1.1.3.3.3.2
		fmPRTransmitterBLocalMode OBJECT-TYPE
			SYNTAX LocalRemote
			MAX-ACCESS read-only
			STATUS current
			DESCRIPTION
				"Passive reserve. Local mode of transmitter B
				
				(0) undefined
				(1) local
				(2) remote"
			::= { fmPRTransmitterB 2 }

		
		-- 1.3.6.1.4.1.19831.1.1.3.3.3.3
		fmPRTransmitterBFault OBJECT-TYPE
			SYNTAX FaultOK
			MAX-ACCESS read-only
			STATUS current
			DESCRIPTION
				"Passive reserve. Fault state of transmitters B
				
				(0) undefined
				(1) fault
				(2) ok"
			::= { fmPRTransmitterB 3 }

		
		-- 1.3.6.1.4.1.19831.1.1.3.3.3.4
		fmPRTransmitterBWarning OBJECT-TYPE
			SYNTAX WarningOK
			MAX-ACCESS read-only
			STATUS current
			DESCRIPTION
				"Passive reserve. Warning state of transmiters B 
				
				(0) undefined
				(1) warning
				(2) ok"
			::= { fmPRTransmitterB 4 }

		
-- fm passive reserve: switch for Event
		-- 1.3.6.1.4.1.19831.1.1.3.3.4
		fmPREventEnable OBJECT IDENTIFIER ::= { fmPassiveReserve 4 }

		
-- fm passive reserve general: switch for Event
		-- 1.3.6.1.4.1.19831.1.1.3.3.4.1
		fmPREventEnableGeneral OBJECT IDENTIFIER ::= { fmPREventEnable 1 }

		
		-- 1.3.6.1.4.1.19831.1.1.3.3.4.1.1
		fmPRPreselectionTransmitterEnable OBJECT-TYPE
			SYNTAX TruthValue
			MAX-ACCESS read-write
			STATUS current
			DESCRIPTION
				"Description.Enable/Disable switch for fmPRPreselectionTransmitter event"
			::= { fmPREventEnableGeneral 1 }

		
		-- 1.3.6.1.4.1.19831.1.1.3.3.4.1.2
		fmPRMainTransmitterOpModeEnable OBJECT-TYPE
			SYNTAX TruthValue
			MAX-ACCESS read-write
			STATUS current
			DESCRIPTION
				"Description.Enable/Disable switch for fmPRMainTransmitterOpMode event"
			::= { fmPREventEnableGeneral 2 }

		
		-- 1.3.6.1.4.1.19831.1.1.3.3.4.1.3
		fmPRReserveControlEnable OBJECT-TYPE
			SYNTAX TruthValue
			MAX-ACCESS read-write
			STATUS current
			DESCRIPTION
				"Description.Enable/Disable switch for fmPRReserveControl event"
			::= { fmPREventEnableGeneral 3 }

		
		-- 1.3.6.1.4.1.19831.1.1.3.3.4.1.4
		fmPRCurrentMainTransmitterEnable OBJECT-TYPE
			SYNTAX TruthValue
			MAX-ACCESS read-write
			STATUS current
			DESCRIPTION
				"Description.Enable/Disable switch for fmPRCurrentMainTransmitter event"
			::= { fmPREventEnableGeneral 4 }

		
		-- 1.3.6.1.4.1.19831.1.1.3.3.4.1.5
		fmPRLocalModeEnable OBJECT-TYPE
			SYNTAX TruthValue
			MAX-ACCESS read-write
			STATUS current
			DESCRIPTION
				"Description.Enable/Disable switch for fmPRLocalMode event"
			::= { fmPREventEnableGeneral 5 }

		
		-- 1.3.6.1.4.1.19831.1.1.3.3.4.1.6
		fmPRControlUnitFaultEnable OBJECT-TYPE
			SYNTAX TruthValue
			MAX-ACCESS read-write
			STATUS current
			DESCRIPTION
				"Description.Enable/Disable switch for fmPRControlUnitFault event"
			::= { fmPREventEnableGeneral 6 }

		
		-- 1.3.6.1.4.1.19831.1.1.3.3.4.1.7
		fmPRSwitchOverModeEnable OBJECT-TYPE
			SYNTAX TruthValue
			MAX-ACCESS read-write
			STATUS current
			DESCRIPTION
				"Description.Enable/Disable switch for fmPRSwitchOverMode event"
			::= { fmPREventEnableGeneral 7 }

		
		-- 1.3.6.1.4.1.19831.1.1.3.3.4.1.8
		fmPRSwitchOverReadyEnable OBJECT-TYPE
			SYNTAX TruthValue
			MAX-ACCESS read-write
			STATUS current
			DESCRIPTION
				"Description.Enable/Disable switch for fmPRSwitchOverReady event"
			::= { fmPREventEnableGeneral 8 }

		
		-- 1.3.6.1.4.1.19831.1.1.3.3.4.1.9
		fmPRSwitchOverExecutedEnable OBJECT-TYPE
			SYNTAX TruthValue
			MAX-ACCESS read-write
			STATUS current
			DESCRIPTION
				"Description.Enable/Disable switch for fmPRSwitchOverExecuted event"
			::= { fmPREventEnableGeneral 9 }

		
		-- 1.3.6.1.4.1.19831.1.1.3.3.4.1.10
		fmPRSwitchOverFaultEnable OBJECT-TYPE
			SYNTAX TruthValue
			MAX-ACCESS read-write
			STATUS current
			DESCRIPTION
				"Description.Enable/Disable switch for fmPRSwitchOverFault event"
			::= { fmPREventEnableGeneral 10 }

		
-- fm passive reserve transmitter A: switch for Event
		-- 1.3.6.1.4.1.19831.1.1.3.3.4.2
		fmPREventEnableTransmitterA OBJECT IDENTIFIER ::= { fmPREventEnable 2 }

		
		-- 1.3.6.1.4.1.19831.1.1.3.3.4.2.1
		fmPRTransmitterARFPresentEnable OBJECT-TYPE
			SYNTAX TruthValue
			MAX-ACCESS read-write
			STATUS current
			DESCRIPTION
				"Description.Enable/Disable switch for fmPRTransmitterARFPresent event"
			::= { fmPREventEnableTransmitterA 1 }

		
		-- 1.3.6.1.4.1.19831.1.1.3.3.4.2.2
		fmPRTransmitterALocalModeEnable OBJECT-TYPE
			SYNTAX TruthValue
			MAX-ACCESS read-write
			STATUS current
			DESCRIPTION
				"Description.Enable/Disable switch for fmPRTransmitterALocalMode event"
			::= { fmPREventEnableTransmitterA 2 }

		
		-- 1.3.6.1.4.1.19831.1.1.3.3.4.2.3
		fmPRTransmitterAFaultEnable OBJECT-TYPE
			SYNTAX TruthValue
			MAX-ACCESS read-write
			STATUS current
			DESCRIPTION
				"Description.Enable/Disable switch for fmPRTransmitterAFault event"
			::= { fmPREventEnableTransmitterA 3 }

		
		-- 1.3.6.1.4.1.19831.1.1.3.3.4.2.4
		fmPRTransmitterAWarningEnable OBJECT-TYPE
			SYNTAX TruthValue
			MAX-ACCESS read-write
			STATUS current
			DESCRIPTION
				"Description.Enable/Disable switch for fmPRTransmitterAWarning event"
			::= { fmPREventEnableTransmitterA 4 }

		
-- fm passive reserve transmitter B: switch for Event
		-- 1.3.6.1.4.1.19831.1.1.3.3.4.3
		fmPREventEnableTransmitterB OBJECT IDENTIFIER ::= { fmPREventEnable 3 }

		
		-- 1.3.6.1.4.1.19831.1.1.3.3.4.3.1
		fmPRTransmitterBRFPresentEnable OBJECT-TYPE
			SYNTAX TruthValue
			MAX-ACCESS read-write
			STATUS current
			DESCRIPTION
				"Description.Enable/Disable switch for fmPRTransmitterBRFPresent event"
			::= { fmPREventEnableTransmitterB 1 }

		
		-- 1.3.6.1.4.1.19831.1.1.3.3.4.3.2
		fmPRTransmitterBLocalModeEnable OBJECT-TYPE
			SYNTAX TruthValue
			MAX-ACCESS read-write
			STATUS current
			DESCRIPTION
				"Description.Enable/Disable switch for fmPRTransmitterBLocalMode event"
			::= { fmPREventEnableTransmitterB 2 }

		
		-- 1.3.6.1.4.1.19831.1.1.3.3.4.3.3
		fmPRTransmitterBFaultEnable OBJECT-TYPE
			SYNTAX TruthValue
			MAX-ACCESS read-write
			STATUS current
			DESCRIPTION
				"Description.Enable/Disable switch for fmPRAmplifierBFault event"
			::= { fmPREventEnableTransmitterB 3 }

		
		-- 1.3.6.1.4.1.19831.1.1.3.3.4.3.4
		fmPRTransmitterBWarningEnable OBJECT-TYPE
			SYNTAX TruthValue
			MAX-ACCESS read-write
			STATUS current
			DESCRIPTION
				"Description.Enable/Disable switch for fmPRAmplifierBWarning event"
			::= { fmPREventEnableTransmitterB 4 }

		
-- fm passive reserve event priority
		-- 1.3.6.1.4.1.19831.1.1.3.3.5
		fmPREventPriority OBJECT IDENTIFIER ::= { fmPassiveReserve 5 }

		
-- fm passive reserve event priority general
		-- 1.3.6.1.4.1.19831.1.1.3.3.5.1
		fmPREventPriorityGeneral OBJECT IDENTIFIER ::= { fmPREventPriority 1 }

		
		-- 1.3.6.1.4.1.19831.1.1.3.3.5.1.1
		fmPRPreselectionTransmitterPriority OBJECT-TYPE
			SYNTAX Unsigned32
			MAX-ACCESS read-write
			STATUS current
			DESCRIPTION
				"Description.Priority for fmPRPreselectionTransmitter event"
			::= { fmPREventPriorityGeneral 1 }

		
		-- 1.3.6.1.4.1.19831.1.1.3.3.5.1.2
		fmPRMainTransmitterOpModePriority OBJECT-TYPE
			SYNTAX Unsigned32
			MAX-ACCESS read-write
			STATUS current
			DESCRIPTION
				"Description.Priority for fmPRMainTransmitterOpMode event"
			::= { fmPREventPriorityGeneral 2 }

		
		-- 1.3.6.1.4.1.19831.1.1.3.3.5.1.3
		fmRReserveControlPriority OBJECT-TYPE
			SYNTAX Unsigned32
			MAX-ACCESS read-write
			STATUS current
			DESCRIPTION
				"Description.Priority for fmPRReserveControl event"
			::= { fmPREventPriorityGeneral 3 }

		
		-- 1.3.6.1.4.1.19831.1.1.3.3.5.1.4
		fmPRCurrentMainTransmitterPriority OBJECT-TYPE
			SYNTAX Unsigned32
			MAX-ACCESS read-write
			STATUS current
			DESCRIPTION
				"Description.Priority for fmPRCurrentMainTransmitter event"
			::= { fmPREventPriorityGeneral 4 }

		
		-- 1.3.6.1.4.1.19831.1.1.3.3.5.1.5
		fmPRLocalModePriority OBJECT-TYPE
			SYNTAX Unsigned32
			MAX-ACCESS read-write
			STATUS current
			DESCRIPTION
				"Description.Priority for fmPRLocalMode event"
			::= { fmPREventPriorityGeneral 5 }

		
		-- 1.3.6.1.4.1.19831.1.1.3.3.5.1.6
		fmPRControlUnitFaultPriority OBJECT-TYPE
			SYNTAX Unsigned32
			MAX-ACCESS read-write
			STATUS current
			DESCRIPTION
				"Description.Priority for fmPRControlUnitFault event"
			::= { fmPREventPriorityGeneral 6 }

		
		-- 1.3.6.1.4.1.19831.1.1.3.3.5.1.7
		fmPRSwitchOverModePriority OBJECT-TYPE
			SYNTAX Unsigned32
			MAX-ACCESS read-write
			STATUS current
			DESCRIPTION
				"Description.Priority for fmPRSwitchOverMode event"
			::= { fmPREventPriorityGeneral 7 }

		
		-- 1.3.6.1.4.1.19831.1.1.3.3.5.1.8
		fmPRSwitchOverReadyPriority OBJECT-TYPE
			SYNTAX Unsigned32
			MAX-ACCESS read-write
			STATUS current
			DESCRIPTION
				"Description.Priority for fmPRSwitchOverReady event"
			::= { fmPREventPriorityGeneral 8 }

		
		-- 1.3.6.1.4.1.19831.1.1.3.3.5.1.9
		fmPRSwitchOverExecutedPriority OBJECT-TYPE
			SYNTAX Unsigned32
			MAX-ACCESS read-write
			STATUS current
			DESCRIPTION
				"Description.Priority for fmPRSwitchOverExecuted event"
			::= { fmPREventPriorityGeneral 9 }

		
		-- 1.3.6.1.4.1.19831.1.1.3.3.5.1.10
		fmPRSwitchOverFaultPriority OBJECT-TYPE
			SYNTAX Unsigned32
			MAX-ACCESS read-write
			STATUS current
			DESCRIPTION
				"Description.Priority for fmPRSwitchOverFault event"
			::= { fmPREventPriorityGeneral 10 }

		
-- fm passive reserve event priority transmitter A
		-- 1.3.6.1.4.1.19831.1.1.3.3.5.2
		fmPREventPriorityTransmitteA OBJECT IDENTIFIER ::= { fmPREventPriority 2 }

		
		-- 1.3.6.1.4.1.19831.1.1.3.3.5.2.1
		fmPRTransmitterARFPresentPriority OBJECT-TYPE
			SYNTAX Unsigned32
			MAX-ACCESS read-write
			STATUS current
			DESCRIPTION
				"Description.Priority for fmPRTransmitterARFPresent event"
			::= { fmPREventPriorityTransmitteA 1 }

		
		-- 1.3.6.1.4.1.19831.1.1.3.3.5.2.2
		fmPRTransmitterALocalModePriority OBJECT-TYPE
			SYNTAX Unsigned32
			MAX-ACCESS read-write
			STATUS current
			DESCRIPTION
				"Description.Priority for fmPRTransmitterALocalMode event"
			::= { fmPREventPriorityTransmitteA 2 }

		
		-- 1.3.6.1.4.1.19831.1.1.3.3.5.2.3
		fmPRTransmitterAFaultPriority OBJECT-TYPE
			SYNTAX Unsigned32
			MAX-ACCESS read-write
			STATUS current
			DESCRIPTION
				"Description.Priority for fmPRTransmitterAFault event"
			::= { fmPREventPriorityTransmitteA 3 }

		
		-- 1.3.6.1.4.1.19831.1.1.3.3.5.2.4
		fmPRTransmitterAWarningPriority OBJECT-TYPE
			SYNTAX Unsigned32
			MAX-ACCESS read-write
			STATUS current
			DESCRIPTION
				"Description.Priority for fmPRTransmitterAWarning event"
			::= { fmPREventPriorityTransmitteA 4 }

		
-- fm passive reserve event priority transmitter B 
		-- 1.3.6.1.4.1.19831.1.1.3.3.5.3
		fmPREventPriorityTransmitterB OBJECT IDENTIFIER ::= { fmPREventPriority 3 }

		
		-- 1.3.6.1.4.1.19831.1.1.3.3.5.3.1
		fmPRTransmitterBRFPresentPriority OBJECT-TYPE
			SYNTAX Unsigned32
			MAX-ACCESS read-write
			STATUS current
			DESCRIPTION
				"Description.Priority for fmPRTransmitterBRFPresent event"
			::= { fmPREventPriorityTransmitterB 1 }

		
		-- 1.3.6.1.4.1.19831.1.1.3.3.5.3.2
		fmPRTransmitterBLocalModePriority OBJECT-TYPE
			SYNTAX Unsigned32
			MAX-ACCESS read-write
			STATUS current
			DESCRIPTION
				"Description.Priority for fmPRTransmitterBLocalMode event"
			::= { fmPREventPriorityTransmitterB 2 }

		
		-- 1.3.6.1.4.1.19831.1.1.3.3.5.3.3
		fmPRTransmitterBFaultPriority OBJECT-TYPE
			SYNTAX Unsigned32
			MAX-ACCESS read-write
			STATUS current
			DESCRIPTION
				"Description.Priority for fmPRAmplifierBFault event"
			::= { fmPREventPriorityTransmitterB 3 }

		
		-- 1.3.6.1.4.1.19831.1.1.3.3.5.3.4
		fmPRTransmitterBWarningPriority OBJECT-TYPE
			SYNTAX Unsigned32
			MAX-ACCESS read-write
			STATUS current
			DESCRIPTION
				"Description.Priority for fmPRAmplifierBWarning event"
			::= { fmPREventPriorityTransmitterB 4 }

		
		-- 1.3.6.1.4.1.19831.1.1.3.3.6
		groupsPR OBJECT IDENTIFIER ::= { fmPassiveReserve 6 }

		
		-- 1.3.6.1.4.1.19831.1.1.3.3.6.1
		obgectGroupPR OBJECT-GROUP
			OBJECTS { fmPRMainTransmitterOpMode, fmPRReserveControl, fmPRCurrentMainTransmitter, fmPRLocalMode, fmPRControlUnitFault, 
				fmPRSwitchOverMode, fmPRSwitchOverReady, fmPRSwitchOverExecuted, fmPRSwitchOverFault, fmPRTransmitterARFPresent, 
				fmPRTransmitterAFault, fmPRTransmitterAWarning, fmPRTransmitterBRFPresent, fmPRTransmitterBFault, fmPRTransmitterBWarning, 
				fmPRMainTransmitterOpModeEnable, fmPRReserveControlEnable, fmPRCurrentMainTransmitterEnable, fmPRLocalModeEnable, fmPRControlUnitFaultEnable, 
				fmPRSwitchOverModeEnable, fmPRSwitchOverReadyEnable, fmPRSwitchOverExecutedEnable, fmPRSwitchOverFaultEnable, fmPRTransmitterARFPresentEnable, 
				fmPRTransmitterAFaultEnable, fmPRTransmitterAWarningEnable, fmPRTransmitterBRFPresentEnable, fmPRTransmitterBFaultEnable, fmPRTransmitterBWarningEnable, 
				fmPRMainTransmitterOpModePriority, fmRReserveControlPriority, fmPRCurrentMainTransmitterPriority, fmPRLocalModePriority, fmPRControlUnitFaultPriority, 
				fmPRSwitchOverModePriority, fmPRSwitchOverReadyPriority, fmPRSwitchOverExecutedPriority, fmPRSwitchOverFaultPriority, fmPRTransmitterARFPresentPriority, 
				fmPRTransmitterAFaultPriority, fmPRTransmitterAWarningPriority, fmPRTransmitterBRFPresentPriority, fmPRTransmitterBFaultPriority, fmPRTransmitterALocalMode, 
				fmPRTransmitterBLocalMode, fmPRTransmitterALocalModeEnable, fmPRTransmitterBLocalModeEnable, fmPRTransmitterALocalModePriority, fmPRTransmitterBLocalModePriority, 
				fmPRTransmitterBWarningPriority, fmPRPreselectionTransmitter, fmPRPreselectionTransmitterEnable, fmPRPreselectionTransmitterPriority }
			STATUS current
			DESCRIPTION 
				"Description. fm passive reserve objects group"
			::= { groupsPR 1 }

		
		-- 1.3.6.1.4.1.19831.1.1.3.3.6.2
		eventGrpupPR NOTIFICATION-GROUP
			NOTIFICATIONS { fmPRMainTransmitterOpModeEvent, fmPRReserveControlEvent, fmPRCurrentMainTransmitterEvent, fmPRLocalModeEvent, fmPRControlUnitFaultEvent, 
				fmPRSwitchOverModeEvent, fmPRSwitchOverReadyEvent, fmPRSwitchOverExecutedEvent, fmPRSwitchOverFaultEvent, fmPRTransmitterARFPresentEvent, 
				fmPRTransmitterAFaultEvent, fmPRTransmitterAWarningEvent, fmPRTransmitterBRFPresentEvent, fmPRTransmitterBFaultEvent, fmPRTransmitterALocalModeEvent, 
				fmPRTransmitterBLocalModeEvent, fmPRTransmitterBWarningEvent, fmPRPreselectionTransmitterEvent }
			STATUS current
			DESCRIPTION 
				"Description. fm passive reserve events"
			::= { groupsPR 2 }

		
		-- 1.3.6.1.4.1.19831.1.1.3.3.7
		compliance OBJECT IDENTIFIER ::= { fmPassiveReserve 7 }

		
		-- 1.3.6.1.4.1.19831.1.1.3.3.7.1
		fmPassiveReserveCompliance MODULE-COMPLIANCE
			STATUS current
			DESCRIPTION 
				"Compliance Statement"
			MODULE -- this module
				MANDATORY-GROUPS { obgectGroupPR, eventGrpupPR }
			::= { compliance 1 }

		
	
	END

--
-- IRT-FM-PASSIVERESERVE-MIB.my
--
