--
-- IRT-DVBT-PASSIVERESERVE-MIB.my
-- MIB generated by MG-SOFT Visual MIB Builder Version 6.0  Build 88
-- Friday, May 04, 2007 at 17:46:48
--

	IRT-DVBT-PASSIVERESERVE-MIB DEFINITIONS ::= BEGIN
 
		IMPORTS
			eventTimeStamp, eventPriority, eventCounter, mibRelease			
				FROM IRT-COMMONVARBINDS-MIB			
			dvbT, Input1Input2, SelectManualAuto, SelectOnOff, LocalRemote, 
			FaultOK, ReadyNotReady, ExecutedNotExecuted, PresentNotPresent, WarningOK, 
			OkNotOk, MuteOk, SFNMFN			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DisplayString, TruthValue			
				FROM SNMPv2-TC;
	
	
		-- 1.3.6.1.4.1.19831.1.1.1.3
		dvbPassiveReserve MODULE-IDENTITY 
			LAST-UPDATED "200705041400Z"		-- May 04, 2007 at 14:00 GMT
			ORGANIZATION 
				"IRT for WORKING-GROUP-TC-MIB"
			CONTACT-INFO 
				"Contact Info.
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				
				branch definition
				
				1st level
				
				events               OBJECT IDENTIFIER ::= { dvbPassiveReserve 0 }
				dvbPRGeneral         OBJECT IDENTIFIER ::= { dvbPassiveReserve 1 }
				dvbPRTransmitterA    OBJECT IDENTIFIER ::= { dvbPassiveReserve 2 }
				dvbPRTransmitterB    OBJECT IDENTIFIER ::= { dvbPassiveReserve 3 }
				dvbPREventEnable     OBJECT IDENTIFIER ::= { dvbPassiveReserve 4 }
				dvbPREventPriority   OBJECT IDENTIFIER ::= { dvbPassiveReserve 5 }
				groups               OBJECT IDENTIFIER ::= { dvbPassiveReserve 6 }
				
				2nd level
				
				dvbPREventEnableGeneral        OBJECT IDENTIFIER ::= { dvbPREventEnable 1 }
				dvbPREventEnableTransmitterA   OBJECT IDENTIFIER ::= { dvbPREventEnable 2 }
				dvbPREventEnableTransmitterB   OBJECT IDENTIFIER ::= { dvbPREventEnable 3 }
				
				dvbPREventPriorityGeneral        OBJECT IDENTIFIER ::= { dvbPREventPriority 1 }
				dvbPREventPriorityTransmitterA   OBJECT IDENTIFIER ::= { dvbPREventPriority 2 }
				dvbPREventPriorityTransmitterB   OBJECT IDENTIFIER ::= { dvbPREventPriority 3 }
				
				 end branch"
			REVISION "200705041400Z"		-- May 04, 2007 at 14:00 GMT
			DESCRIPTION 
				"change SFNMode, LocalMode (description only) and Module-COMPLIANCE"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dvbT 3 }

		
	
	
--
-- Node definitions
--
	
-- dvb passive transmitter events 
		-- 1.3.6.1.4.1.19831.1.1.1.3.0
		dvbEventsPR OBJECT IDENTIFIER ::= { dvbPassiveReserve 0 }

		
		-- 1.3.6.1.4.1.19831.1.1.1.3.0.1
		dvbPRInputPreselectionEvent NOTIFICATION-TYPE
			OBJECTS { sysDescr, sysName, sysLocation, eventTimeStamp, eventPriority, 
				eventCounter, dvbPRInputPreselection }
			STATUS current
			DESCRIPTION 
				"Description. dvbPRInputPreselection notification"
			::= { dvbEventsPR 1 }

		
		-- 1.3.6.1.4.1.19831.1.1.1.3.0.2
		dvbPRInputAutomaticEvent NOTIFICATION-TYPE
			OBJECTS { sysDescr, sysName, sysLocation, eventTimeStamp, eventPriority, 
				eventCounter, dvbPRInputAutomatic }
			STATUS current
			DESCRIPTION 
				"Description. dvbPRInputAutomatic notification"
			::= { dvbEventsPR 2 }

		
		-- 1.3.6.1.4.1.19831.1.1.1.3.0.3
		dvbPRPreselectionTransmitterEvent NOTIFICATION-TYPE
			OBJECTS { sysDescr, sysName, sysLocation, eventTimeStamp, eventPriority, 
				eventCounter, dvbPRPreselectionTransmitter }
			STATUS current
			DESCRIPTION 
				"Description. dvbPRPreselectionTransmitter notification"
			::= { dvbEventsPR 3 }

		
		-- 1.3.6.1.4.1.19831.1.1.1.3.0.4
		dvbPRMainTransmitterOpModeEvent NOTIFICATION-TYPE
			OBJECTS { sysDescr, sysName, sysLocation, eventTimeStamp, eventPriority, 
				eventCounter, dvbPRMainTransmitterOpMode }
			STATUS current
			DESCRIPTION 
				"Description. dvbPRMainTransmitterOpMode notification"
			::= { dvbEventsPR 4 }

		
		-- 1.3.6.1.4.1.19831.1.1.1.3.0.5
		dvbPRReserveControlEvent NOTIFICATION-TYPE
			OBJECTS { sysDescr, sysName, sysLocation, eventTimeStamp, eventPriority, 
				eventCounter, dvbPRReserveControl }
			STATUS current
			DESCRIPTION 
				"Description. dvbPRReserveControl notification"
			::= { dvbEventsPR 5 }

		
		-- 1.3.6.1.4.1.19831.1.1.1.3.0.6
		dvbPRResetFaultEvent NOTIFICATION-TYPE
			OBJECTS { sysDescr, sysName, sysLocation, eventTimeStamp, eventPriority, 
				eventCounter, dvbPRResetFault }
			STATUS obsolete
			DESCRIPTION 
				"Notification is inactive!
				
				
				Description. dvbPRResetFault notification"
			::= { dvbEventsPR 6 }

		
		-- 1.3.6.1.4.1.19831.1.1.1.3.0.7
		dvbPRCurrentMainTransmitterEvent NOTIFICATION-TYPE
			OBJECTS { sysDescr, sysName, sysLocation, eventTimeStamp, eventPriority, 
				eventCounter, dvbPRCurrentMainTransmitter }
			STATUS current
			DESCRIPTION 
				"Description. dvbPRCurrentMainTransmitter notification"
			::= { dvbEventsPR 7 }

		
		-- 1.3.6.1.4.1.19831.1.1.1.3.0.8
		dvbPRLocalModeEvent NOTIFICATION-TYPE
			OBJECTS { sysDescr, sysName, sysLocation, eventTimeStamp, eventPriority, 
				eventCounter, dvbPRLocalMode }
			STATUS current
			DESCRIPTION 
				"Description. dvbPRLocalMode notification"
			::= { dvbEventsPR 8 }

		
		-- 1.3.6.1.4.1.19831.1.1.1.3.0.9
		dvbPRControlUnitFaultEvent NOTIFICATION-TYPE
			OBJECTS { sysDescr, sysName, sysLocation, eventTimeStamp, eventPriority, 
				eventCounter, dvbPRControlUnitFault }
			STATUS current
			DESCRIPTION 
				"Description. dvbPRControlUnitFault notification"
			::= { dvbEventsPR 9 }

		
		-- 1.3.6.1.4.1.19831.1.1.1.3.0.10
		dvbPRSwitchOverModeEvent NOTIFICATION-TYPE
			OBJECTS { sysDescr, sysName, sysLocation, eventTimeStamp, eventPriority, 
				eventCounter, dvbPRSwitchOverMode }
			STATUS current
			DESCRIPTION 
				"Description. dvbPRSwitchOverMode notification"
			::= { dvbEventsPR 10 }

		
		-- 1.3.6.1.4.1.19831.1.1.1.3.0.11
		dvbPRSwitchOverReadyEvent NOTIFICATION-TYPE
			OBJECTS { sysDescr, sysName, sysLocation, eventTimeStamp, eventPriority, 
				eventCounter, dvbPRSwitchOverReady }
			STATUS current
			DESCRIPTION 
				"Description. dvbPRSwitchOverReady notification"
			::= { dvbEventsPR 11 }

		
		-- 1.3.6.1.4.1.19831.1.1.1.3.0.12
		dvbPRSwitchOverExecutedEvent NOTIFICATION-TYPE
			OBJECTS { sysDescr, sysName, sysLocation, eventTimeStamp, eventPriority, 
				eventCounter, dvbPRSwitchOverExecuted }
			STATUS current
			DESCRIPTION 
				"Description. dvbPRSwitchOverExecuted notification"
			::= { dvbEventsPR 12 }

		
		-- 1.3.6.1.4.1.19831.1.1.1.3.0.13
		dvbPRSwitchOverFaultEvent NOTIFICATION-TYPE
			OBJECTS { sysDescr, sysName, sysLocation, eventTimeStamp, eventPriority, 
				eventCounter, dvbPRSwitchOverFault }
			STATUS current
			DESCRIPTION 
				"Description. dvbPRSwitchOverFault notification"
			::= { dvbEventsPR 13 }

		
		-- 1.3.6.1.4.1.19831.1.1.1.3.0.14
		dvbPRTransmitterARFPresentEvent NOTIFICATION-TYPE
			OBJECTS { sysDescr, sysName, sysLocation, eventTimeStamp, eventPriority, 
				eventCounter, dvbPRTransmitterARFPresent }
			STATUS current
			DESCRIPTION 
				"Description. dvbPRTransmitterARFPresent notification"
			::= { dvbEventsPR 14 }

		
		-- 1.3.6.1.4.1.19831.1.1.1.3.0.15
		dvbPRTransmitterAFaultEvent NOTIFICATION-TYPE
			OBJECTS { sysDescr, sysName, sysLocation, eventTimeStamp, eventPriority, 
				eventCounter, dvbPRTransmitterAFault }
			STATUS current
			DESCRIPTION 
				"Description. dvbPRTransmitterAFault notification"
			::= { dvbEventsPR 15 }

		
		-- 1.3.6.1.4.1.19831.1.1.1.3.0.16
		dvbPRTransmitterAWarningEvent NOTIFICATION-TYPE
			OBJECTS { sysDescr, sysName, sysLocation, eventTimeStamp, eventPriority, 
				eventCounter, dvbPRTransmitterAWarning }
			STATUS current
			DESCRIPTION 
				"Description. dvbPRTransmitterAWarning notification"
			::= { dvbEventsPR 16 }

		
		-- 1.3.6.1.4.1.19831.1.1.1.3.0.17
		dvbPRTransmitterAInput1OKEvent NOTIFICATION-TYPE
			OBJECTS { sysDescr, sysName, sysLocation, eventTimeStamp, eventPriority, 
				eventCounter, dvbPRTransmitterAInput1OK }
			STATUS current
			DESCRIPTION 
				"Description. dvbPRTransmitterAInput1OK notification"
			::= { dvbEventsPR 17 }

		
		-- 1.3.6.1.4.1.19831.1.1.1.3.0.18
		dvbPRTransmitterAInput2OKEvent NOTIFICATION-TYPE
			OBJECTS { sysDescr, sysName, sysLocation, eventTimeStamp, eventPriority, 
				eventCounter, dvbPRTransmitterAInput2OK }
			STATUS current
			DESCRIPTION 
				"Description. dvbPRTransmitterAInput2OK notification"
			::= { dvbEventsPR 18 }

		
		-- 1.3.6.1.4.1.19831.1.1.1.3.0.19
		dvbPRTransmitterALocalModeEvent NOTIFICATION-TYPE
			OBJECTS { sysDescr, sysName, sysLocation, eventTimeStamp, eventPriority, 
				eventCounter, dvbPRTransmitterALocalMode }
			STATUS current
			DESCRIPTION 
				"Description. dvbPRTransmitterALocalMode notification"
			::= { dvbEventsPR 19 }

		
		-- 1.3.6.1.4.1.19831.1.1.1.3.0.20
		dvbPRTransmitterAActiveInputEvent NOTIFICATION-TYPE
			OBJECTS { sysDescr, sysName, sysLocation, eventTimeStamp, eventPriority, 
				eventCounter, dvbPRTransmitterAActiveInput }
			STATUS current
			DESCRIPTION 
				"Description. dvbPRTransmitterAActiveInput notification"
			::= { dvbEventsPR 20 }

		
		-- 1.3.6.1.4.1.19831.1.1.1.3.0.21
		dvbPRTransmitterASFNModeEvent NOTIFICATION-TYPE
			OBJECTS { sysDescr, sysName, sysLocation, eventTimeStamp, eventPriority, 
				eventCounter, dvbPRTransmitterASFNMode }
			STATUS current
			DESCRIPTION 
				"Description. dvbPRTransmitterASFNMode notification"
			::= { dvbEventsPR 21 }

		
		-- 1.3.6.1.4.1.19831.1.1.1.3.0.22
		dvbPRTransmitterARefFaultEvent NOTIFICATION-TYPE
			OBJECTS { sysDescr, sysName, sysLocation, eventTimeStamp, eventPriority, 
				eventCounter, dvbPRTransmitterARefFault }
			STATUS current
			DESCRIPTION 
				"Description. dvbPRTransmitterARefFault notification"
			::= { dvbEventsPR 22 }

		
		-- 1.3.6.1.4.1.19831.1.1.1.3.0.23
		dvbPRTransmitterAFaultMIPEvent NOTIFICATION-TYPE
			OBJECTS { sysDescr, sysName, sysLocation, eventTimeStamp, eventPriority, 
				eventCounter, dvbPRTransmitterAFaultMIP }
			STATUS current
			DESCRIPTION 
				"Description. dvbPRTransmitterAFaultMIP notification"
			::= { dvbEventsPR 23 }

		
		-- 1.3.6.1.4.1.19831.1.1.1.3.0.24
		dvbPRTransmitterAMuteEvent NOTIFICATION-TYPE
			OBJECTS { sysDescr, sysName, sysLocation, eventTimeStamp, eventPriority, 
				eventCounter, dvbPRTransmitterAMute }
			STATUS current
			DESCRIPTION 
				"Description. dvbPRTransmitterAMute notification"
			::= { dvbEventsPR 24 }

		
		-- 1.3.6.1.4.1.19831.1.1.1.3.0.25
		dvbPRTransmitterAStuffingModeEvent NOTIFICATION-TYPE
			OBJECTS { sysDescr, sysName, sysLocation, eventTimeStamp, eventPriority, 
				eventCounter, dvbPRTransmitterAStuffingMode }
			STATUS current
			DESCRIPTION 
				"Description. dvbPRTransmitterAStuffingMode notification"
			::= { dvbEventsPR 25 }

		
		-- 1.3.6.1.4.1.19831.1.1.1.3.0.26
		dvbPRTransmitterBRFPresentEvent NOTIFICATION-TYPE
			OBJECTS { sysDescr, sysName, sysLocation, eventTimeStamp, eventPriority, 
				eventCounter, dvbPRTransmitterBRFPresent }
			STATUS current
			DESCRIPTION 
				"Description. dvbPRTransmitterBRFPresent notification"
			::= { dvbEventsPR 26 }

		
		-- 1.3.6.1.4.1.19831.1.1.1.3.0.27
		dvbPRTransmitterBFaultEvent NOTIFICATION-TYPE
			OBJECTS { sysDescr, sysName, sysLocation, eventTimeStamp, eventPriority, 
				eventCounter, dvbPRTransmitterBFault }
			STATUS current
			DESCRIPTION 
				"Description. dvbPRTransmitterBFault notification"
			::= { dvbEventsPR 27 }

		
		-- 1.3.6.1.4.1.19831.1.1.1.3.0.28
		dvbPRTransmitterBWarningEvent NOTIFICATION-TYPE
			OBJECTS { sysDescr, sysName, sysLocation, eventTimeStamp, eventPriority, 
				eventCounter, dvbPRTransmitterBWarning }
			STATUS current
			DESCRIPTION 
				"Description. dvbPRTransmitterBWarning notification"
			::= { dvbEventsPR 28 }

		
		-- 1.3.6.1.4.1.19831.1.1.1.3.0.29
		dvbPRTransmitterBInput1OKEvent NOTIFICATION-TYPE
			OBJECTS { sysDescr, sysName, sysLocation, eventTimeStamp, eventPriority, 
				eventCounter, dvbPRTransmitterBInput1OK }
			STATUS current
			DESCRIPTION 
				"Description. dvbPRTransmitterBInput1OK notification"
			::= { dvbEventsPR 29 }

		
		-- 1.3.6.1.4.1.19831.1.1.1.3.0.30
		dvbPRTransmitterBInput2OKEvent NOTIFICATION-TYPE
			OBJECTS { sysDescr, sysName, sysLocation, eventTimeStamp, eventPriority, 
				eventCounter, dvbPRTransmitterBInput2OK }
			STATUS current
			DESCRIPTION 
				"Description. dvbPRTransmitterBInput2OK notification"
			::= { dvbEventsPR 30 }

		
		-- 1.3.6.1.4.1.19831.1.1.1.3.0.31
		dvbPRTransmitterBLocalModeEvent NOTIFICATION-TYPE
			OBJECTS { sysDescr, sysName, sysLocation, eventTimeStamp, eventPriority, 
				eventCounter, dvbPRTransmitterBLocalMode }
			STATUS current
			DESCRIPTION 
				"Description. dvbPRTransmitterBLocalMode notofication"
			::= { dvbEventsPR 31 }

		
		-- 1.3.6.1.4.1.19831.1.1.1.3.0.32
		dvbPRTransmitterBActiveInputEvent NOTIFICATION-TYPE
			OBJECTS { sysDescr, sysName, sysLocation, eventTimeStamp, eventPriority, 
				eventCounter, dvbPRTransmitterBActiveInput }
			STATUS current
			DESCRIPTION 
				"Description. dvbPRTransmitterBActiveInput notification"
			::= { dvbEventsPR 32 }

		
		-- 1.3.6.1.4.1.19831.1.1.1.3.0.33
		dvbPRTransmitterBSFNModeEvent NOTIFICATION-TYPE
			OBJECTS { sysDescr, sysName, sysLocation, eventTimeStamp, eventPriority, 
				eventCounter, dvbPRTransmitterASFNMode }
			STATUS current
			DESCRIPTION 
				"Description. dvbPRTransmitterBSFNMode notification"
			::= { dvbEventsPR 33 }

		
		-- 1.3.6.1.4.1.19831.1.1.1.3.0.34
		dvbPRTransmitterBRefFaultEvent NOTIFICATION-TYPE
			OBJECTS { sysDescr, sysName, sysLocation, eventTimeStamp, eventPriority, 
				eventCounter, dvbPRTransmitterBRefFault }
			STATUS current
			DESCRIPTION 
				"Description. dvbPRTransmitterBRefFault notification"
			::= { dvbEventsPR 34 }

		
		-- 1.3.6.1.4.1.19831.1.1.1.3.0.35
		dvbPRTransmitterBFaultMIPEvent NOTIFICATION-TYPE
			OBJECTS { sysDescr, sysName, sysLocation, eventTimeStamp, eventPriority, 
				eventCounter, dvbPRTransmitterBFaultMIP }
			STATUS current
			DESCRIPTION 
				"Description. dvbPRTransmitterBFaultMIP notification"
			::= { dvbEventsPR 35 }

		
		-- 1.3.6.1.4.1.19831.1.1.1.3.0.36
		dvbPRTransmitterBMuteEvent NOTIFICATION-TYPE
			OBJECTS { sysDescr, sysName, sysLocation, eventTimeStamp, eventPriority, 
				eventCounter, dvbPRTransmitterBMute }
			STATUS current
			DESCRIPTION 
				"Description. dvbPRTransmitterBMute notification"
			::= { dvbEventsPR 36 }

		
		-- 1.3.6.1.4.1.19831.1.1.1.3.0.37
		dvbPRTransmitterBStuffingModeEvent NOTIFICATION-TYPE
			OBJECTS { sysDescr, sysName, sysLocation, eventTimeStamp, eventPriority, 
				eventCounter, dvbPRTransmitterBStuffingMode }
			STATUS current
			DESCRIPTION 
				"Description. dvbPRTransmitterBStuffingMode notification"
			::= { dvbEventsPR 37 }

		
-- dvb passive reserve general
		-- 1.3.6.1.4.1.19831.1.1.1.3.1
		dvbPRGeneral OBJECT IDENTIFIER ::= { dvbPassiveReserve 1 }

		
		-- 1.3.6.1.4.1.19831.1.1.1.3.1.1
		dvbPRInputPreselection OBJECT-TYPE
			SYNTAX Input1Input2
			MAX-ACCESS read-write
			STATUS current
			DESCRIPTION
				"Preselection input of passive reserve
				
				(0) undefined
				(1) Input 1
				(2) Input 2"
			::= { dvbPRGeneral 1 }

		
		-- 1.3.6.1.4.1.19831.1.1.1.3.1.2
		dvbPRInputAutomatic OBJECT-TYPE
			SYNTAX SelectManualAuto
			MAX-ACCESS read-write
			STATUS current
			DESCRIPTION
				"Passive reserve. Input selection mode manual or automatic
				
				(0) undefined
				(1) manual 
				(2) automatic"
			::= { dvbPRGeneral 2 }

		
		-- 1.3.6.1.4.1.19831.1.1.1.3.1.3
		dvbPRPreselectionTransmitter OBJECT-TYPE
			SYNTAX INTEGER
				{
				undefined(0),
				transmitterA(1),
				transmitterB(2)
				}
			MAX-ACCESS read-write
			STATUS current
			DESCRIPTION
				"Passive reserve. Preselection of the transmitter 
				
				"
			::= { dvbPRGeneral 3 }

		
		-- 1.3.6.1.4.1.19831.1.1.1.3.1.4
		dvbPRMainTransmitterOpMode OBJECT-TYPE
			SYNTAX SelectOnOff
			MAX-ACCESS read-write
			STATUS current
			DESCRIPTION
				"Passive reserve. General transmitter control 
				
				(0) undefined
				(1) ON
				(2) OFF"
			::= { dvbPRGeneral 4 }

		
		-- 1.3.6.1.4.1.19831.1.1.1.3.1.5
		dvbPRReserveControl OBJECT-TYPE
			SYNTAX SelectOnOff
			MAX-ACCESS read-write
			STATUS current
			DESCRIPTION
				"Passive reserve. Reserve control 
				
				(0) undefined
				(1) ON 
				(2) OFF "
			::= { dvbPRGeneral 5 }

		
		-- 1.3.6.1.4.1.19831.1.1.1.3.1.6
		dvbPRResetFault OBJECT-TYPE
			SYNTAX Unsigned32
			MAX-ACCESS read-write
			STATUS obsolete
			DESCRIPTION
				"Description. Massage is inactive!
				
				Reset fault:trigger for reset the sum fault
				
				<1>
				
				1: reset sum fault"
			::= { dvbPRGeneral 6 }

		
		-- 1.3.6.1.4.1.19831.1.1.1.3.1.7
		dvbPRCurrentMainTransmitter OBJECT-TYPE
			SYNTAX INTEGER
				{
				undefined(0),
				transmitterA(1),
				transmitterB(2)
				}
			MAX-ACCESS read-only
			STATUS current
			DESCRIPTION
				"Passive reserve. Transmitter antenna mode
				
				
				"
			::= { dvbPRGeneral 7 }

		
		-- 1.3.6.1.4.1.19831.1.1.1.3.1.8
		dvbPRLocalMode OBJECT-TYPE
			SYNTAX LocalRemote
			MAX-ACCESS read-only
			STATUS current
			DESCRIPTION
				"Passive reserve. Local mode
				
				(0) undefined
				(1) local
				(2) remote"
			::= { dvbPRGeneral 8 }

		
		-- 1.3.6.1.4.1.19831.1.1.1.3.1.9
		dvbPRControlUnitFault OBJECT-TYPE
			SYNTAX FaultOK
			MAX-ACCESS read-only
			STATUS current
			DESCRIPTION
				"Passive reserve. State of the control unit
				
				(0) undefined
				(1) fault
				(2) ok"
			::= { dvbPRGeneral 9 }

		
		-- 1.3.6.1.4.1.19831.1.1.1.3.1.10
		dvbPRSwitchOverMode OBJECT-TYPE
			SYNTAX SelectManualAuto
			MAX-ACCESS read-write
			STATUS current
			DESCRIPTION
				"Passive reserve. Switch over mode manual or automatic
				
				(0) undefined
				(1) manual 
				(2) automatic"
			::= { dvbPRGeneral 10 }

		
		-- 1.3.6.1.4.1.19831.1.1.1.3.1.11
		dvbPRSwitchOverReady OBJECT-TYPE
			SYNTAX ReadyNotReady
			MAX-ACCESS read-only
			STATUS current
			DESCRIPTION
				"State of the passive reserve switch over unit
				
				(0) undefined
				(1) ready
				(2) not ready"
			::= { dvbPRGeneral 11 }

		
		-- 1.3.6.1.4.1.19831.1.1.1.3.1.12
		dvbPRSwitchOverExecuted OBJECT-TYPE
			SYNTAX ExecutedNotExecuted
			MAX-ACCESS read-only
			STATUS current
			DESCRIPTION
				"Passive reserve.Shows if the reserve switch over unit it has executed
				
				(0) undefined
				(1) executed
				(2) not executed"
			::= { dvbPRGeneral 12 }

		
		-- 1.3.6.1.4.1.19831.1.1.1.3.1.13
		dvbPRSwitchOverFault OBJECT-TYPE
			SYNTAX FaultOK
			MAX-ACCESS read-only
			STATUS current
			DESCRIPTION
				"Passive reserve. Fault state of the switch over unit
				
				(0) undefined
				(1) faulty
				(2) ok"
			::= { dvbPRGeneral 13 }

		
-- dvb passive transmitter A
		-- 1.3.6.1.4.1.19831.1.1.1.3.2
		dvbPRTransmitterA OBJECT IDENTIFIER ::= { dvbPassiveReserve 2 }

		
		-- 1.3.6.1.4.1.19831.1.1.1.3.2.1
		dvbPRTransmitterARFPresent OBJECT-TYPE
			SYNTAX PresentNotPresent
			MAX-ACCESS read-only
			STATUS current
			DESCRIPTION
				"Passive reserve. Describes if the output power of the  transmitter A is present
				
				(0) undefined
				(1) present
				(2) not present"
			::= { dvbPRTransmitterA 1 }

		
		-- 1.3.6.1.4.1.19831.1.1.1.3.2.2
		dvbPRTransmitterAFault OBJECT-TYPE
			SYNTAX FaultOK
			MAX-ACCESS read-only
			STATUS current
			DESCRIPTION
				"Passive reserve. Fault state of transmitter A
				
				(0) undefined
				(1) fault
				(2) ok"
			::= { dvbPRTransmitterA 2 }

		
		-- 1.3.6.1.4.1.19831.1.1.1.3.2.3
		dvbPRTransmitterAWarning OBJECT-TYPE
			SYNTAX WarningOK
			MAX-ACCESS read-only
			STATUS current
			DESCRIPTION
				"Passive reserve. Warning state of transmitter A 
				
				(0) undefined
				(1) warning
				(2) ok"
			::= { dvbPRTransmitterA 3 }

		
		-- 1.3.6.1.4.1.19831.1.1.1.3.2.4
		dvbPRTransmitterAInput1OK OBJECT-TYPE
			SYNTAX OkNotOk
			MAX-ACCESS read-only
			STATUS current
			DESCRIPTION
				"Passive reserve. Describes if the input signal at the input 1 of transmitter A  is ok
				
				(0) undefined
				(1) signal ok
				(2) signal is not ok"
			::= { dvbPRTransmitterA 4 }

		
		-- 1.3.6.1.4.1.19831.1.1.1.3.2.5
		dvbPRTransmitterAInput2OK OBJECT-TYPE
			SYNTAX OkNotOk
			MAX-ACCESS read-only
			STATUS current
			DESCRIPTION
				"Passive reserve. Describes if the input signal at the input 2 of transmitter A  is ok
				
				(0) undefined
				(1) signal ok
				(2) signal is not ok"
			::= { dvbPRTransmitterA 5 }

		
		-- 1.3.6.1.4.1.19831.1.1.1.3.2.6
		dvbPRTransmitterALocalMode OBJECT-TYPE
			SYNTAX LocalRemote
			MAX-ACCESS read-only
			STATUS current
			DESCRIPTION
				"Passive reserve. Local mode of transmitter A
				
				(0) undefined
				(1) local
				(2) remote"
			::= { dvbPRTransmitterA 6 }

		
		-- 1.3.6.1.4.1.19831.1.1.1.3.2.7
		dvbPRTransmitterAActiveInput OBJECT-TYPE
			SYNTAX INTEGER
				{
				undfined(0),
				input1(1),
				input2(2),
				seamless(3),
				hmHierarchicalModulation(4)
				}
			MAX-ACCESS read-only
			STATUS current
			DESCRIPTION
				"Passive Resereve. Active Input of the transmitter A 
				
				"
			::= { dvbPRTransmitterA 7 }

		
		-- 1.3.6.1.4.1.19831.1.1.1.3.2.8
		dvbPRTransmitterASFNMode OBJECT-TYPE
			SYNTAX SFNMFN
			MAX-ACCESS read-only
			STATUS current
			DESCRIPTION
				"Passive reserve. SFN mode of transmitter A
				
				(0) undefined
				(1) SFN
				(2) MFN"
			::= { dvbPRTransmitterA 8 }

		
		-- 1.3.6.1.4.1.19831.1.1.1.3.2.9
		dvbPRTransmitterARefFault OBJECT-TYPE
			SYNTAX FaultOK
			MAX-ACCESS read-only
			STATUS current
			DESCRIPTION
				"Passive reserve. Fault state of the GPS input or the reference frequency of transmitter A
				
				(0) undefined
				(1) fault
				(2) ok"
			::= { dvbPRTransmitterA 9 }

		
		-- 1.3.6.1.4.1.19831.1.1.1.3.2.10
		dvbPRTransmitterAFaultMIP OBJECT-TYPE
			SYNTAX FaultOK
			MAX-ACCESS read-only
			STATUS current
			DESCRIPTION
				"Passive reserve. MIP fault state of transmitter A
				
				(0) undefined
				(1) fault
				(2) ok"
			::= { dvbPRTransmitterA 10 }

		
		-- 1.3.6.1.4.1.19831.1.1.1.3.2.11
		dvbPRTransmitterAMute OBJECT-TYPE
			SYNTAX MuteOk
			MAX-ACCESS read-only
			STATUS current
			DESCRIPTION
				"Passive reserve. Mute state of transmitter A
				
				(0) undefined
				(1) mute
				(2) ok"
			::= { dvbPRTransmitterA 11 }

		
		-- 1.3.6.1.4.1.19831.1.1.1.3.2.12
		dvbPRTransmitterAStuffingMode OBJECT-TYPE
			SYNTAX SelectOnOff
			MAX-ACCESS read-only
			STATUS current
			DESCRIPTION
				"Passive reserve. Stuffing state of transmitter A
				
				(0) undefined
				(1) ON 
				(2) OFF "
			::= { dvbPRTransmitterA 12 }

		
-- dvb passive transmitter B
		-- 1.3.6.1.4.1.19831.1.1.1.3.3
		dvbPRTransmitterB OBJECT IDENTIFIER ::= { dvbPassiveReserve 3 }

		
		-- 1.3.6.1.4.1.19831.1.1.1.3.3.1
		dvbPRTransmitterBRFPresent OBJECT-TYPE
			SYNTAX PresentNotPresent
			MAX-ACCESS read-only
			STATUS current
			DESCRIPTION
				"Passive reserve. Describes if the output power of the  transmitter B is present
				
				(0) undefined
				(1) present
				(2) not present"
			::= { dvbPRTransmitterB 1 }

		
		-- 1.3.6.1.4.1.19831.1.1.1.3.3.2
		dvbPRTransmitterBFault OBJECT-TYPE
			SYNTAX FaultOK
			MAX-ACCESS read-only
			STATUS current
			DESCRIPTION
				"Passive reserve. Fault state of transmitters B
				
				(0) undefined
				(1) fault
				(2) ok"
			::= { dvbPRTransmitterB 2 }

		
		-- 1.3.6.1.4.1.19831.1.1.1.3.3.3
		dvbPRTransmitterBWarning OBJECT-TYPE
			SYNTAX WarningOK
			MAX-ACCESS read-only
			STATUS current
			DESCRIPTION
				"Passive reserve. Warning state of transmiters B 
				
				(0) undefined
				(1) warning
				(2) ok"
			::= { dvbPRTransmitterB 3 }

		
		-- 1.3.6.1.4.1.19831.1.1.1.3.3.4
		dvbPRTransmitterBInput1OK OBJECT-TYPE
			SYNTAX OkNotOk
			MAX-ACCESS read-only
			STATUS current
			DESCRIPTION
				"Passive reserve. Describes if the input signal at the input 1 of transmitterB is ok
				
				(0) undefined
				(1) signal ok
				(2) signal is not ok"
			::= { dvbPRTransmitterB 4 }

		
		-- 1.3.6.1.4.1.19831.1.1.1.3.3.5
		dvbPRTransmitterBInput2OK OBJECT-TYPE
			SYNTAX OkNotOk
			MAX-ACCESS read-only
			STATUS current
			DESCRIPTION
				"Passive reserve. Describes if the input signal at the input 2 of transmitter B is ok
				
				(0) undefined
				(1) signal ok
				(2) signal is not ok "
			::= { dvbPRTransmitterB 5 }

		
		-- 1.3.6.1.4.1.19831.1.1.1.3.3.6
		dvbPRTransmitterBLocalMode OBJECT-TYPE
			SYNTAX LocalRemote
			MAX-ACCESS read-only
			STATUS current
			DESCRIPTION
				"Passive reserve. Local mode of transmitter A
				
				(0) undefined
				(1) local
				(2) remote"
			::= { dvbPRTransmitterB 6 }

		
		-- 1.3.6.1.4.1.19831.1.1.1.3.3.7
		dvbPRTransmitterBActiveInput OBJECT-TYPE
			SYNTAX INTEGER
				{
				undefined(0),
				input1(1),
				input2(2),
				seamless(3),
				hmHierarchicalModulation(4)
				}
			MAX-ACCESS read-only
			STATUS current
			DESCRIPTION
				"Passive reserve. Active input of the transmitter B 
				
				"
			::= { dvbPRTransmitterB 7 }

		
		-- 1.3.6.1.4.1.19831.1.1.1.3.3.8
		dvbPRTransmitterBSFNMode OBJECT-TYPE
			SYNTAX SFNMFN
			MAX-ACCESS read-only
			STATUS current
			DESCRIPTION
				"Passive reserve. SFN mode of transmitter B
				
				(0) undefined
				(1) SFN
				(2) MFN"
			::= { dvbPRTransmitterB 8 }

		
		-- 1.3.6.1.4.1.19831.1.1.1.3.3.9
		dvbPRTransmitterBRefFault OBJECT-TYPE
			SYNTAX FaultOK
			MAX-ACCESS read-only
			STATUS current
			DESCRIPTION
				"Passive reserve. Fault state of the GPS input or the reference frequency of transmitter B
				
				(0) undefined
				(1) fault
				(2) ok"
			::= { dvbPRTransmitterB 9 }

		
		-- 1.3.6.1.4.1.19831.1.1.1.3.3.10
		dvbPRTransmitterBMute OBJECT-TYPE
			SYNTAX MuteOk
			MAX-ACCESS read-only
			STATUS current
			DESCRIPTION
				"Passive reserve. Mute state of transmitter B
				
				(0) undefined
				(1) mute
				(2) ok"
			::= { dvbPRTransmitterB 10 }

		
		-- 1.3.6.1.4.1.19831.1.1.1.3.3.11
		dvbPRTransmitterBFaultMIP OBJECT-TYPE
			SYNTAX FaultOK
			MAX-ACCESS read-only
			STATUS current
			DESCRIPTION
				"Passive reserve. MIP fault state of transmitter B
				
				(0) undefined
				(1) (fault)
				(2) (ok)"
			::= { dvbPRTransmitterB 11 }

		
		-- 1.3.6.1.4.1.19831.1.1.1.3.3.12
		dvbPRTransmitterBStuffingMode OBJECT-TYPE
			SYNTAX SelectOnOff
			MAX-ACCESS read-only
			STATUS current
			DESCRIPTION
				"Passive reserve. Stuffing state of transmitter B
				
				(0) undefined
				(1) ON 
				(2) OFF "
			::= { dvbPRTransmitterB 12 }

		
-- dvb passive reserve switch for events
		-- 1.3.6.1.4.1.19831.1.1.1.3.4
		dvbPREventEnable OBJECT IDENTIFIER ::= { dvbPassiveReserve 4 }

		
-- dvb passive reserve general: switch for Event
		-- 1.3.6.1.4.1.19831.1.1.1.3.4.1
		dvbPREventEnableGeneral OBJECT IDENTIFIER ::= { dvbPREventEnable 1 }

		
		-- 1.3.6.1.4.1.19831.1.1.1.3.4.1.1
		dvbPRInputPreselectionEnable OBJECT-TYPE
			SYNTAX TruthValue
			MAX-ACCESS read-write
			STATUS current
			DESCRIPTION
				"Description.Enable/Disable switch for dvbARInputPreselection event"
			::= { dvbPREventEnableGeneral 1 }

		
		-- 1.3.6.1.4.1.19831.1.1.1.3.4.1.2
		dvbPRInputAutomaticEnable OBJECT-TYPE
			SYNTAX TruthValue
			MAX-ACCESS read-write
			STATUS current
			DESCRIPTION
				"Description.Enable/Disable switch for dvbARInputAutomatic event"
			::= { dvbPREventEnableGeneral 2 }

		
		-- 1.3.6.1.4.1.19831.1.1.1.3.4.1.3
		dvbPRPreselectionTransmitterEnable OBJECT-TYPE
			SYNTAX TruthValue
			MAX-ACCESS read-write
			STATUS current
			DESCRIPTION
				"Description.Enable/Disable switch for dvbPRPreselectionTransmitter event"
			::= { dvbPREventEnableGeneral 3 }

		
		-- 1.3.6.1.4.1.19831.1.1.1.3.4.1.4
		dvbPRMainTransmitterOpModeEnable OBJECT-TYPE
			SYNTAX TruthValue
			MAX-ACCESS read-write
			STATUS current
			DESCRIPTION
				"Description.Enable/Disable switch for dvbPRMainTransmitterOpMode event"
			::= { dvbPREventEnableGeneral 4 }

		
		-- 1.3.6.1.4.1.19831.1.1.1.3.4.1.5
		dvbPRReserveControlEnable OBJECT-TYPE
			SYNTAX TruthValue
			MAX-ACCESS read-write
			STATUS current
			DESCRIPTION
				"Description.Enable/Disable switch for dvbPRReserveControl event"
			::= { dvbPREventEnableGeneral 5 }

		
		-- 1.3.6.1.4.1.19831.1.1.1.3.4.1.6
		dvbPRResetFaultEnable OBJECT-TYPE
			SYNTAX TruthValue
			MAX-ACCESS read-write
			STATUS obsolete
			DESCRIPTION
				"Massage is inactive!
				
				Description. Enable/Disable switch for dvbPRResetFault event"
			::= { dvbPREventEnableGeneral 6 }

		
		-- 1.3.6.1.4.1.19831.1.1.1.3.4.1.7
		dvbPRCurrentMainTransmitterEnable OBJECT-TYPE
			SYNTAX TruthValue
			MAX-ACCESS read-write
			STATUS current
			DESCRIPTION
				"Description.Enable/Disable switch for dvbPRCurrentMainTransmitter event"
			::= { dvbPREventEnableGeneral 7 }

		
		-- 1.3.6.1.4.1.19831.1.1.1.3.4.1.8
		dvbPRLocalModeEnable OBJECT-TYPE
			SYNTAX TruthValue
			MAX-ACCESS read-write
			STATUS current
			DESCRIPTION
				"Description.Enable/Disable switch for dvbPRLocalMode event"
			::= { dvbPREventEnableGeneral 8 }

		
		-- 1.3.6.1.4.1.19831.1.1.1.3.4.1.9
		dvbPRControlUnitFaultEnable OBJECT-TYPE
			SYNTAX TruthValue
			MAX-ACCESS read-write
			STATUS current
			DESCRIPTION
				"Description.Enable/Disable switch for dvbPRControlUnitFault event"
			::= { dvbPREventEnableGeneral 9 }

		
		-- 1.3.6.1.4.1.19831.1.1.1.3.4.1.10
		dvbPRSwitchOverModeEnable OBJECT-TYPE
			SYNTAX TruthValue
			MAX-ACCESS read-write
			STATUS current
			DESCRIPTION
				"Description.Enable/Disable switch for dvbPRSwitchOverMode event"
			::= { dvbPREventEnableGeneral 10 }

		
		-- 1.3.6.1.4.1.19831.1.1.1.3.4.1.11
		dvbPRSwitchOverReadyEnable OBJECT-TYPE
			SYNTAX TruthValue
			MAX-ACCESS read-write
			STATUS current
			DESCRIPTION
				"Description.Enable/Disable switch for dvbPRSwitchOverReady event"
			::= { dvbPREventEnableGeneral 11 }

		
		-- 1.3.6.1.4.1.19831.1.1.1.3.4.1.12
		dvbPRSwitchOverExecutedEnable OBJECT-TYPE
			SYNTAX TruthValue
			MAX-ACCESS read-write
			STATUS current
			DESCRIPTION
				"Description.Enable/Disable switch for dvbPRSwitchOverExecuted event"
			::= { dvbPREventEnableGeneral 12 }

		
		-- 1.3.6.1.4.1.19831.1.1.1.3.4.1.13
		dvbPRSwitchOverFaultEnable OBJECT-TYPE
			SYNTAX TruthValue
			MAX-ACCESS read-write
			STATUS current
			DESCRIPTION
				"Description.Enable/Disable switch for dvbPRSwitchOverFault event"
			::= { dvbPREventEnableGeneral 13 }

		
-- dvb passive reserve transmitter A: switch for Event
		-- 1.3.6.1.4.1.19831.1.1.1.3.4.2
		dvbPREventEnableTransmitterA OBJECT IDENTIFIER ::= { dvbPREventEnable 2 }

		
		-- 1.3.6.1.4.1.19831.1.1.1.3.4.2.1
		dvbPRTransmitterARFPresentEnable OBJECT-TYPE
			SYNTAX TruthValue
			MAX-ACCESS read-write
			STATUS current
			DESCRIPTION
				"Description.Enable/Disable switch for dvbPRTransmitterARFPresent event"
			::= { dvbPREventEnableTransmitterA 1 }

		
		-- 1.3.6.1.4.1.19831.1.1.1.3.4.2.2
		dvbPRTransmitterAFaultEnable OBJECT-TYPE
			SYNTAX TruthValue
			MAX-ACCESS read-write
			STATUS current
			DESCRIPTION
				"Description.Enable/Disable switch for dvbPRTransmitterAFault event"
			::= { dvbPREventEnableTransmitterA 2 }

		
		-- 1.3.6.1.4.1.19831.1.1.1.3.4.2.3
		dvbPRTransmitterAWarningEnable OBJECT-TYPE
			SYNTAX TruthValue
			MAX-ACCESS read-write
			STATUS current
			DESCRIPTION
				"Description.Enable/Disable switch for dvbPRTransmitterAWarning event"
			::= { dvbPREventEnableTransmitterA 3 }

		
		-- 1.3.6.1.4.1.19831.1.1.1.3.4.2.4
		dvbPRTransmitterAInput1OKEnable OBJECT-TYPE
			SYNTAX TruthValue
			MAX-ACCESS read-write
			STATUS current
			DESCRIPTION
				"Description.Enable/Disable switch for dvbPRTransmitterAInput1OK event"
			::= { dvbPREventEnableTransmitterA 4 }

		
		-- 1.3.6.1.4.1.19831.1.1.1.3.4.2.5
		dvbPRTransmitterAInput2OKEnable OBJECT-TYPE
			SYNTAX TruthValue
			MAX-ACCESS read-write
			STATUS current
			DESCRIPTION
				"Description.Enable/Disable switch for dvbPRTransmitterAInput2OK event"
			::= { dvbPREventEnableTransmitterA 5 }

		
		-- 1.3.6.1.4.1.19831.1.1.1.3.4.2.6
		dvbPRTransmitterALocalModeEnable OBJECT-TYPE
			SYNTAX TruthValue
			MAX-ACCESS read-write
			STATUS current
			DESCRIPTION
				"Description.Enable/Disable switch for dvbPRTransmitterALocalMode event"
			::= { dvbPREventEnableTransmitterA 6 }

		
		-- 1.3.6.1.4.1.19831.1.1.1.3.4.2.7
		dvbPRTransmitterAActiveInputEnable OBJECT-TYPE
			SYNTAX TruthValue
			MAX-ACCESS read-write
			STATUS current
			DESCRIPTION
				"Description.Enable/Disable switch for dvbPRTransmitterAActiveInput event"
			::= { dvbPREventEnableTransmitterA 7 }

		
		-- 1.3.6.1.4.1.19831.1.1.1.3.4.2.8
		dvbPRTransmitterASFNModeEnable OBJECT-TYPE
			SYNTAX TruthValue
			MAX-ACCESS read-write
			STATUS current
			DESCRIPTION
				"Description.Enable/Disable switch for dvbPRTransmitterASFNMode event"
			::= { dvbPREventEnableTransmitterA 8 }

		
		-- 1.3.6.1.4.1.19831.1.1.1.3.4.2.9
		dvbPRTransmitterARefFaultEnable OBJECT-TYPE
			SYNTAX TruthValue
			MAX-ACCESS read-write
			STATUS current
			DESCRIPTION
				"Description.Enable/Disable switch for dvbPRTransmitterARefFault event"
			::= { dvbPREventEnableTransmitterA 9 }

		
		-- 1.3.6.1.4.1.19831.1.1.1.3.4.2.10
		dvbPRTransmitterAFaultMIPEnable OBJECT-TYPE
			SYNTAX TruthValue
			MAX-ACCESS read-write
			STATUS current
			DESCRIPTION
				"Description.Enable/Disable switch for dvbPRTransmitterAFaultMIP event"
			::= { dvbPREventEnableTransmitterA 10 }

		
		-- 1.3.6.1.4.1.19831.1.1.1.3.4.2.11
		dvbPRTransmitterAMuteEnable OBJECT-TYPE
			SYNTAX TruthValue
			MAX-ACCESS read-write
			STATUS current
			DESCRIPTION
				"Description.Enable/Disable switch for dvbPRTransmitterAMute event"
			::= { dvbPREventEnableTransmitterA 11 }

		
		-- 1.3.6.1.4.1.19831.1.1.1.3.4.2.12
		dvbPRTransmitterAStuffingModeEnable OBJECT-TYPE
			SYNTAX TruthValue
			MAX-ACCESS read-write
			STATUS current
			DESCRIPTION
				"Description.Enable/Disable switch for dvbPRTransmitterAStuffingMode event"
			::= { dvbPREventEnableTransmitterA 12 }

		
-- dvb passive reserve transmitter B: switch for Event
		-- 1.3.6.1.4.1.19831.1.1.1.3.4.3
		dvbPREventEnableTransmitterB OBJECT IDENTIFIER ::= { dvbPREventEnable 3 }

		
		-- 1.3.6.1.4.1.19831.1.1.1.3.4.3.1
		dvbPRTransmitterBRFPresentEnable OBJECT-TYPE
			SYNTAX TruthValue
			MAX-ACCESS read-write
			STATUS current
			DESCRIPTION
				"Description.Enable/Disable switch for dvbPRTransmitterBRFPresent event"
			::= { dvbPREventEnableTransmitterB 1 }

		
		-- 1.3.6.1.4.1.19831.1.1.1.3.4.3.2
		dvbPRTransmitterBFaultEnable OBJECT-TYPE
			SYNTAX TruthValue
			MAX-ACCESS read-write
			STATUS current
			DESCRIPTION
				"Description.Enable/Disable switch for dvbPRAmplifierBFault event"
			::= { dvbPREventEnableTransmitterB 2 }

		
		-- 1.3.6.1.4.1.19831.1.1.1.3.4.3.3
		dvbPRTransmitterBWarningEnable OBJECT-TYPE
			SYNTAX TruthValue
			MAX-ACCESS read-write
			STATUS current
			DESCRIPTION
				"Description.Enable/Disable switch for dvbPRAmplifierBWarning event"
			::= { dvbPREventEnableTransmitterB 3 }

		
		-- 1.3.6.1.4.1.19831.1.1.1.3.4.3.4
		dvbPRTransmitterBInput1OKEnable OBJECT-TYPE
			SYNTAX TruthValue
			MAX-ACCESS read-write
			STATUS current
			DESCRIPTION
				"Description.Enable/Disable switch for dvbPRTransmitterBInput1OK event"
			::= { dvbPREventEnableTransmitterB 4 }

		
		-- 1.3.6.1.4.1.19831.1.1.1.3.4.3.5
		dvbPRTransmitterBInput2OKEnable OBJECT-TYPE
			SYNTAX TruthValue
			MAX-ACCESS read-write
			STATUS current
			DESCRIPTION
				"Description.Enable/Disable switch for dvbPRTransmitterBInput2OK event"
			::= { dvbPREventEnableTransmitterB 5 }

		
		-- 1.3.6.1.4.1.19831.1.1.1.3.4.3.6
		dvbPRTransmitterBLocalModeEnable OBJECT-TYPE
			SYNTAX TruthValue
			MAX-ACCESS read-write
			STATUS current
			DESCRIPTION
				"Description.Enable/Disable switch for dvbPRTransmitterBLocalMode event"
			::= { dvbPREventEnableTransmitterB 6 }

		
		-- 1.3.6.1.4.1.19831.1.1.1.3.4.3.7
		dvbPRTransmitterBActiveInputEnable OBJECT-TYPE
			SYNTAX TruthValue
			MAX-ACCESS read-write
			STATUS current
			DESCRIPTION
				"Description.Enable/Disable switch for dvbPRSwitchOverFault event"
			::= { dvbPREventEnableTransmitterB 7 }

		
		-- 1.3.6.1.4.1.19831.1.1.1.3.4.3.8
		dvbPRTransmitterBSFNModeEnable OBJECT-TYPE
			SYNTAX TruthValue
			MAX-ACCESS read-write
			STATUS current
			DESCRIPTION
				"Description.Enable/Disable switch for dvbPRTransmitterBSFNMode event
				"
			::= { dvbPREventEnableTransmitterB 8 }

		
		-- 1.3.6.1.4.1.19831.1.1.1.3.4.3.9
		dvbPRTransmitterBRefFaultEnable OBJECT-TYPE
			SYNTAX TruthValue
			MAX-ACCESS read-write
			STATUS current
			DESCRIPTION
				"Description.Enable/Disable switch for dvbPRTransmitterBRefFault event"
			::= { dvbPREventEnableTransmitterB 9 }

		
		-- 1.3.6.1.4.1.19831.1.1.1.3.4.3.10
		dvbPRTransmitterBMuteEnable OBJECT-TYPE
			SYNTAX TruthValue
			MAX-ACCESS read-write
			STATUS current
			DESCRIPTION
				"Description.Enable/Disable switch for dvbPRTransmitterBMute event"
			::= { dvbPREventEnableTransmitterB 10 }

		
		-- 1.3.6.1.4.1.19831.1.1.1.3.4.3.11
		dvbPRTransmitterBFaultMIPEnable OBJECT-TYPE
			SYNTAX TruthValue
			MAX-ACCESS read-write
			STATUS current
			DESCRIPTION
				"Description.Enable/Disable switch for dvbPRTransmitterBFaultMIP event"
			::= { dvbPREventEnableTransmitterB 11 }

		
		-- 1.3.6.1.4.1.19831.1.1.1.3.4.3.12
		dvbPRTransmitterBStuffingModeEnable OBJECT-TYPE
			SYNTAX TruthValue
			MAX-ACCESS read-write
			STATUS current
			DESCRIPTION
				"Description.Enable/Disable switch for dvbPRTransmitterBStuffingMode event"
			::= { dvbPREventEnableTransmitterB 12 }

		
-- dvb passive reserve event priority
		-- 1.3.6.1.4.1.19831.1.1.1.3.5
		dvbPREventPriority OBJECT IDENTIFIER ::= { dvbPassiveReserve 5 }

		
-- dvb passive reserve event priority general
		-- 1.3.6.1.4.1.19831.1.1.1.3.5.1
		dvbPREventPriorityGeneral OBJECT IDENTIFIER ::= { dvbPREventPriority 1 }

		
		-- 1.3.6.1.4.1.19831.1.1.1.3.5.1.1
		dvbPRInputPreselectionPriority OBJECT-TYPE
			SYNTAX Unsigned32
			MAX-ACCESS read-write
			STATUS current
			DESCRIPTION
				"Description.Priority for dvbPPRInputPreselection event"
			::= { dvbPREventPriorityGeneral 1 }

		
		-- 1.3.6.1.4.1.19831.1.1.1.3.5.1.2
		dvbPRInputAutomaticPriority OBJECT-TYPE
			SYNTAX Unsigned32
			MAX-ACCESS read-write
			STATUS current
			DESCRIPTION
				"Description.Priority for dvbPRInputAutomatic event"
			::= { dvbPREventPriorityGeneral 2 }

		
		-- 1.3.6.1.4.1.19831.1.1.1.3.5.1.3
		dvbPRPreselectionTransmitterPriority OBJECT-TYPE
			SYNTAX Unsigned32
			MAX-ACCESS read-write
			STATUS current
			DESCRIPTION
				"Description.Priority for dvbPRPreselectionTransmitter event"
			::= { dvbPREventPriorityGeneral 3 }

		
		-- 1.3.6.1.4.1.19831.1.1.1.3.5.1.4
		dvbPRMainTransmitterOpModePriority OBJECT-TYPE
			SYNTAX Unsigned32
			MAX-ACCESS read-write
			STATUS current
			DESCRIPTION
				"Description.Priority for dvbPRMainTransmitterOpMode event"
			::= { dvbPREventPriorityGeneral 4 }

		
		-- 1.3.6.1.4.1.19831.1.1.1.3.5.1.5
		dvbPRReserveControlPriority OBJECT-TYPE
			SYNTAX Unsigned32
			MAX-ACCESS read-write
			STATUS current
			DESCRIPTION
				"Description.Priority for dvbPRReserveControl event"
			::= { dvbPREventPriorityGeneral 5 }

		
		-- 1.3.6.1.4.1.19831.1.1.1.3.5.1.6
		dvbPRResetFaultPriority OBJECT-TYPE
			SYNTAX Unsigned32
			MAX-ACCESS read-write
			STATUS obsolete
			DESCRIPTION
				"Massage is inactive!
				
				
				Description. Priority for dvbPRResetFault event"
			::= { dvbPREventPriorityGeneral 6 }

		
		-- 1.3.6.1.4.1.19831.1.1.1.3.5.1.7
		dvbPRCurrentMainTransmitterPriority OBJECT-TYPE
			SYNTAX Unsigned32
			MAX-ACCESS read-write
			STATUS current
			DESCRIPTION
				"Description.Priority for dvbPRCurrentMainTransmitter event"
			::= { dvbPREventPriorityGeneral 7 }

		
		-- 1.3.6.1.4.1.19831.1.1.1.3.5.1.8
		dvbPRLocalModePriority OBJECT-TYPE
			SYNTAX Unsigned32
			MAX-ACCESS read-write
			STATUS current
			DESCRIPTION
				"Description.Priority for dvbPRLocalMode event"
			::= { dvbPREventPriorityGeneral 8 }

		
		-- 1.3.6.1.4.1.19831.1.1.1.3.5.1.9
		dvbPRControlUnitFaultPriority OBJECT-TYPE
			SYNTAX Unsigned32
			MAX-ACCESS read-write
			STATUS current
			DESCRIPTION
				"Description.Priority for dvbPRControlUnitFault event"
			::= { dvbPREventPriorityGeneral 9 }

		
		-- 1.3.6.1.4.1.19831.1.1.1.3.5.1.10
		dvbPRSwitchOverModePriority OBJECT-TYPE
			SYNTAX Unsigned32
			MAX-ACCESS read-write
			STATUS current
			DESCRIPTION
				"Description.Priority for dvbPRSwitchOverMode event"
			::= { dvbPREventPriorityGeneral 10 }

		
		-- 1.3.6.1.4.1.19831.1.1.1.3.5.1.11
		dvbPRSwitchOverReadyPriority OBJECT-TYPE
			SYNTAX Unsigned32
			MAX-ACCESS read-write
			STATUS current
			DESCRIPTION
				"Description.Priority for dvbPRSwitchOverReady event"
			::= { dvbPREventPriorityGeneral 11 }

		
		-- 1.3.6.1.4.1.19831.1.1.1.3.5.1.12
		dvbPRSwitchOverExecutedPriority OBJECT-TYPE
			SYNTAX Unsigned32
			MAX-ACCESS read-write
			STATUS current
			DESCRIPTION
				"Description.Priority for dvbPRSwitchOverExecuted event"
			::= { dvbPREventPriorityGeneral 12 }

		
		-- 1.3.6.1.4.1.19831.1.1.1.3.5.1.13
		dvbPRSwitchOverFaultPriority OBJECT-TYPE
			SYNTAX Unsigned32
			MAX-ACCESS read-write
			STATUS current
			DESCRIPTION
				"Description.Priority for dvbPRSwitchOverFault event"
			::= { dvbPREventPriorityGeneral 13 }

		
-- dvb passive reserve event priority transmitter A
		-- 1.3.6.1.4.1.19831.1.1.1.3.5.2
		dvbPREventPriorityTransmitteA OBJECT IDENTIFIER ::= { dvbPREventPriority 2 }

		
		-- 1.3.6.1.4.1.19831.1.1.1.3.5.2.1
		dvbPRTransmitterARFPresentPriority OBJECT-TYPE
			SYNTAX Unsigned32
			MAX-ACCESS read-write
			STATUS current
			DESCRIPTION
				"Description.Priority for dvbPRTransmitterARFPresent event"
			::= { dvbPREventPriorityTransmitteA 1 }

		
		-- 1.3.6.1.4.1.19831.1.1.1.3.5.2.2
		dvbPRTransmitterAFaultPriority OBJECT-TYPE
			SYNTAX Unsigned32
			MAX-ACCESS read-write
			STATUS current
			DESCRIPTION
				"Description.Priority for dvbPRTransmitterAFault event"
			::= { dvbPREventPriorityTransmitteA 2 }

		
		-- 1.3.6.1.4.1.19831.1.1.1.3.5.2.3
		dvbPRTransmitterAWarningPriority OBJECT-TYPE
			SYNTAX Unsigned32
			MAX-ACCESS read-write
			STATUS current
			DESCRIPTION
				"Description.Priority for dvbPRTransmitterAWarning event"
			::= { dvbPREventPriorityTransmitteA 3 }

		
		-- 1.3.6.1.4.1.19831.1.1.1.3.5.2.4
		dvbPRTransmitterAInput1OKPriority OBJECT-TYPE
			SYNTAX Unsigned32
			MAX-ACCESS read-write
			STATUS current
			DESCRIPTION
				"Description.Priority for dvbPRTransmitterAInput1OK event"
			::= { dvbPREventPriorityTransmitteA 4 }

		
		-- 1.3.6.1.4.1.19831.1.1.1.3.5.2.5
		dvbPRTransmitterAInput2OKPriority OBJECT-TYPE
			SYNTAX Unsigned32
			MAX-ACCESS read-write
			STATUS current
			DESCRIPTION
				"Description.Priority for dvbPRTransmitterAInput2OK event"
			::= { dvbPREventPriorityTransmitteA 5 }

		
		-- 1.3.6.1.4.1.19831.1.1.1.3.5.2.6
		dvbPRTransmitterALocalModePriority OBJECT-TYPE
			SYNTAX Unsigned32
			MAX-ACCESS read-write
			STATUS current
			DESCRIPTION
				"Description.Priority for dvbPRTransmitterALocalMode event"
			::= { dvbPREventPriorityTransmitteA 6 }

		
		-- 1.3.6.1.4.1.19831.1.1.1.3.5.2.7
		dvbPRTransmitterAActiveInputPriority OBJECT-TYPE
			SYNTAX Unsigned32
			MAX-ACCESS read-write
			STATUS current
			DESCRIPTION
				"Description.Priority for dvbPRTransmitterAActiveInput event"
			::= { dvbPREventPriorityTransmitteA 7 }

		
		-- 1.3.6.1.4.1.19831.1.1.1.3.5.2.8
		dvbPRTransmitterASFNModePriority OBJECT-TYPE
			SYNTAX Unsigned32
			MAX-ACCESS read-write
			STATUS current
			DESCRIPTION
				"Description.Priority for dvbPRTransmitterASFNMode event"
			::= { dvbPREventPriorityTransmitteA 8 }

		
		-- 1.3.6.1.4.1.19831.1.1.1.3.5.2.9
		dvbPRTransmitterARefFaultPriority OBJECT-TYPE
			SYNTAX Unsigned32
			MAX-ACCESS read-write
			STATUS current
			DESCRIPTION
				"Description.Priority for dvbPRTransmitterARefFault event"
			::= { dvbPREventPriorityTransmitteA 9 }

		
		-- 1.3.6.1.4.1.19831.1.1.1.3.5.2.10
		dvbPRTransmitterAFaultMIPPriority OBJECT-TYPE
			SYNTAX Unsigned32
			MAX-ACCESS read-write
			STATUS current
			DESCRIPTION
				"Description.Priority for dvbPRTransmitterAFaultMIP event"
			::= { dvbPREventPriorityTransmitteA 10 }

		
		-- 1.3.6.1.4.1.19831.1.1.1.3.5.2.11
		dvbPRTransmitterAMutePriority OBJECT-TYPE
			SYNTAX Unsigned32
			MAX-ACCESS read-write
			STATUS current
			DESCRIPTION
				"Description.Priority for dvbPRTransmitterAMute event"
			::= { dvbPREventPriorityTransmitteA 11 }

		
		-- 1.3.6.1.4.1.19831.1.1.1.3.5.2.12
		dvbPRTransmitterAStuffingModePriority OBJECT-TYPE
			SYNTAX Unsigned32
			MAX-ACCESS read-write
			STATUS current
			DESCRIPTION
				"Description.Priority for dvbPRTransmitterAStuffingMode event"
			::= { dvbPREventPriorityTransmitteA 12 }

		
-- dvb passive reserve event priority transmitter B 
		-- 1.3.6.1.4.1.19831.1.1.1.3.5.3
		dvbPREventPriorityTransmitterB OBJECT IDENTIFIER ::= { dvbPREventPriority 3 }

		
		-- 1.3.6.1.4.1.19831.1.1.1.3.5.3.1
		dvbPRTransmitterBRFPresentPriority OBJECT-TYPE
			SYNTAX Unsigned32
			MAX-ACCESS read-write
			STATUS current
			DESCRIPTION
				"Description.Priority for dvbPRTransmitterBRFPresent event"
			::= { dvbPREventPriorityTransmitterB 1 }

		
		-- 1.3.6.1.4.1.19831.1.1.1.3.5.3.2
		dvbPRTransmitterBFaultPriority OBJECT-TYPE
			SYNTAX Unsigned32
			MAX-ACCESS read-write
			STATUS current
			DESCRIPTION
				"Description.Priority for dvbPRAmplifierBFault event"
			::= { dvbPREventPriorityTransmitterB 2 }

		
		-- 1.3.6.1.4.1.19831.1.1.1.3.5.3.3
		dvbPRTransmitterBWarningPriority OBJECT-TYPE
			SYNTAX Unsigned32
			MAX-ACCESS read-write
			STATUS current
			DESCRIPTION
				"Description.Priority for dvbPRAmplifierBWarning event"
			::= { dvbPREventPriorityTransmitterB 3 }

		
		-- 1.3.6.1.4.1.19831.1.1.1.3.5.3.4
		dvbPRTransmitterBInput1OKPriority OBJECT-TYPE
			SYNTAX Unsigned32
			MAX-ACCESS read-write
			STATUS current
			DESCRIPTION
				"Description.Priority for dvbPRTransmitterBInput1OK event"
			::= { dvbPREventPriorityTransmitterB 4 }

		
		-- 1.3.6.1.4.1.19831.1.1.1.3.5.3.5
		dvbPRTransmitterBInput2OKPriority OBJECT-TYPE
			SYNTAX Unsigned32
			MAX-ACCESS read-write
			STATUS current
			DESCRIPTION
				"Description.Priority for dvbPRTransmitterBInput2OK event"
			::= { dvbPREventPriorityTransmitterB 5 }

		
		-- 1.3.6.1.4.1.19831.1.1.1.3.5.3.6
		dvbPRTransmitterBLocalModePriority OBJECT-TYPE
			SYNTAX Unsigned32
			MAX-ACCESS read-write
			STATUS current
			DESCRIPTION
				"Description.Priority for dvbPRTransmitterBLocalMode event"
			::= { dvbPREventPriorityTransmitterB 6 }

		
		-- 1.3.6.1.4.1.19831.1.1.1.3.5.3.7
		dvbPRTransmitterBActiveInputPriority OBJECT-TYPE
			SYNTAX Unsigned32
			MAX-ACCESS read-write
			STATUS current
			DESCRIPTION
				"Description.Priority for dvbPRTransmitterBActiveInput event"
			::= { dvbPREventPriorityTransmitterB 7 }

		
		-- 1.3.6.1.4.1.19831.1.1.1.3.5.3.8
		dvbPRTransmitterBSFNModePriority OBJECT-TYPE
			SYNTAX Unsigned32
			MAX-ACCESS read-write
			STATUS current
			DESCRIPTION
				"Description.Priority for dvbPRTransmitterBSFNMode event"
			::= { dvbPREventPriorityTransmitterB 8 }

		
		-- 1.3.6.1.4.1.19831.1.1.1.3.5.3.9
		dvbPRTransmitterBRefFaultPriority OBJECT-TYPE
			SYNTAX Unsigned32
			MAX-ACCESS read-write
			STATUS current
			DESCRIPTION
				"Description.Priority for dvbPRTransmitterBRefFault event"
			::= { dvbPREventPriorityTransmitterB 9 }

		
		-- 1.3.6.1.4.1.19831.1.1.1.3.5.3.10
		dvbPRTransmitterBMutePriority OBJECT-TYPE
			SYNTAX Unsigned32
			MAX-ACCESS read-write
			STATUS current
			DESCRIPTION
				"Description.Priority for dvbPRTransmitterBMute event"
			::= { dvbPREventPriorityTransmitterB 10 }

		
		-- 1.3.6.1.4.1.19831.1.1.1.3.5.3.11
		dvbPRTransmitterBFaultMIPPriority OBJECT-TYPE
			SYNTAX Unsigned32
			MAX-ACCESS read-write
			STATUS current
			DESCRIPTION
				"Description.Priority for dvbPRTransmitterBFaultMIP event"
			::= { dvbPREventPriorityTransmitterB 11 }

		
		-- 1.3.6.1.4.1.19831.1.1.1.3.5.3.12
		dvbPRTransmitterBStuffingModePriority OBJECT-TYPE
			SYNTAX Unsigned32
			MAX-ACCESS read-write
			STATUS current
			DESCRIPTION
				"Description.Priority for dvbPRTransmitterBStuffingMode event"
			::= { dvbPREventPriorityTransmitterB 12 }

		
		-- 1.3.6.1.4.1.19831.1.1.1.3.6
		groupsPR OBJECT IDENTIFIER ::= { dvbPassiveReserve 6 }

		
		-- 1.3.6.1.4.1.19831.1.1.1.3.6.1
		obgectGroupPR OBJECT-GROUP
			OBJECTS { dvbPRInputPreselection, dvbPRPreselectionTransmitter, dvbPRMainTransmitterOpMode, dvbPRReserveControl, dvbPRCurrentMainTransmitter, 
				dvbPRLocalMode, dvbPRControlUnitFault, dvbPRSwitchOverMode, dvbPRSwitchOverReady, dvbPRSwitchOverExecuted, 
				dvbPRSwitchOverFault, dvbPRTransmitterARFPresent, dvbPRTransmitterAFault, dvbPRTransmitterAWarning, dvbPRTransmitterAInput1OK, 
				dvbPRTransmitterAInput2OK, dvbPRTransmitterALocalMode, dvbPRTransmitterAActiveInput, dvbPRTransmitterASFNMode, dvbPRTransmitterARefFault, 
				dvbPRTransmitterAFaultMIP, dvbPRTransmitterAMute, dvbPRTransmitterAStuffingMode, dvbPRTransmitterBFault, dvbPRTransmitterBWarning, 
				dvbPRTransmitterBInput1OK, dvbPRTransmitterBInput2OK, dvbPRTransmitterBLocalMode, dvbPRTransmitterBActiveInput, dvbPRTransmitterBSFNMode, 
				dvbPRTransmitterBRefFault, dvbPRTransmitterBMute, dvbPRTransmitterBFaultMIP, dvbPRTransmitterBStuffingMode, dvbPRInputPreselectionEnable, 
				dvbPRInputAutomaticEnable, dvbPRPreselectionTransmitterEnable, dvbPRMainTransmitterOpModeEnable, dvbPRReserveControlEnable, dvbPRCurrentMainTransmitterEnable, 
				dvbPRLocalModeEnable, dvbPRControlUnitFaultEnable, dvbPRSwitchOverModeEnable, dvbPRSwitchOverReadyEnable, dvbPRSwitchOverExecutedEnable, 
				dvbPRSwitchOverFaultEnable, dvbPRTransmitterARFPresentEnable, dvbPRTransmitterAFaultEnable, dvbPRTransmitterAWarningEnable, dvbPRTransmitterAInput1OKEnable, 
				dvbPRTransmitterAInput2OKEnable, dvbPRTransmitterALocalModeEnable, dvbPRTransmitterAActiveInputEnable, dvbPRTransmitterASFNModeEnable, dvbPRTransmitterARefFaultEnable, 
				dvbPRTransmitterAFaultMIPEnable, dvbPRTransmitterAMuteEnable, dvbPRTransmitterAStuffingModeEnable, dvbPRTransmitterBFaultEnable, dvbPRTransmitterBWarningEnable, 
				dvbPRTransmitterBInput1OKEnable, dvbPRTransmitterBInput2OKEnable, dvbPRTransmitterBLocalModeEnable, dvbPRTransmitterBActiveInputEnable, dvbPRTransmitterBSFNModeEnable, 
				dvbPRTransmitterBRefFaultEnable, dvbPRTransmitterBMuteEnable, dvbPRTransmitterBFaultMIPEnable, dvbPRTransmitterBStuffingModeEnable, dvbPRInputPreselectionPriority, 
				dvbPRPreselectionTransmitterPriority, dvbPRMainTransmitterOpModePriority, dvbPRReserveControlPriority, dvbPRCurrentMainTransmitterPriority, dvbPRLocalModePriority, 
				dvbPRControlUnitFaultPriority, dvbPRSwitchOverModePriority, dvbPRSwitchOverReadyPriority, dvbPRSwitchOverExecutedPriority, dvbPRSwitchOverFaultPriority, 
				dvbPRTransmitterARFPresentPriority, dvbPRTransmitterAFaultPriority, dvbPRTransmitterAWarningPriority, dvbPRTransmitterAInput1OKPriority, dvbPRTransmitterAInput2OKPriority, 
				dvbPRTransmitterALocalModePriority, dvbPRTransmitterAActiveInputPriority, dvbPRTransmitterASFNModePriority, dvbPRTransmitterARefFaultPriority, dvbPRTransmitterAFaultMIPPriority, 
				dvbPRTransmitterAMutePriority, dvbPRTransmitterAStuffingModePriority, dvbPRTransmitterBFaultPriority, dvbPRTransmitterBWarningPriority, dvbPRTransmitterBInput1OKPriority, 
				dvbPRTransmitterBInput2OKPriority, dvbPRTransmitterBLocalModePriority, dvbPRTransmitterBActiveInputPriority, dvbPRTransmitterBSFNModePriority, dvbPRTransmitterBRefFaultPriority, 
				dvbPRTransmitterBMutePriority, dvbPRTransmitterBFaultMIPPriority, dvbPRTransmitterBRFPresent, dvbPRTransmitterBStuffingModePriority, dvbPRTransmitterBRFPresentPriority, 
				dvbPRTransmitterBRFPresentEnable, dvbPRInputAutomatic, dvbPRInputAutomaticPriority }
			STATUS current
			DESCRIPTION 
				"Description. objects"
			::= { groupsPR 1 }

		
		-- 1.3.6.1.4.1.19831.1.1.1.3.6.2
		eventGrpupPR NOTIFICATION-GROUP
			NOTIFICATIONS { dvbPRInputPreselectionEvent, dvbPRInputAutomaticEvent, dvbPRPreselectionTransmitterEvent, dvbPRMainTransmitterOpModeEvent, dvbPRReserveControlEvent, 
				dvbPRCurrentMainTransmitterEvent, dvbPRLocalModeEvent, dvbPRControlUnitFaultEvent, dvbPRSwitchOverModeEvent, dvbPRSwitchOverReadyEvent, 
				dvbPRSwitchOverExecutedEvent, dvbPRSwitchOverFaultEvent, dvbPRTransmitterARFPresentEvent, dvbPRTransmitterAFaultEvent, dvbPRTransmitterAWarningEvent, 
				dvbPRTransmitterAInput1OKEvent, dvbPRTransmitterAInput2OKEvent, dvbPRTransmitterALocalModeEvent, dvbPRTransmitterAActiveInputEvent, dvbPRTransmitterASFNModeEvent, 
				dvbPRTransmitterARefFaultEvent, dvbPRTransmitterAFaultMIPEvent, dvbPRTransmitterAMuteEvent, dvbPRTransmitterAStuffingModeEvent, dvbPRTransmitterBRFPresentEvent, 
				dvbPRTransmitterBFaultEvent, dvbPRTransmitterBWarningEvent, dvbPRTransmitterBInput1OKEvent, dvbPRTransmitterBInput2OKEvent, dvbPRTransmitterBLocalModeEvent, 
				dvbPRTransmitterBActiveInputEvent, dvbPRTransmitterBSFNModeEvent, dvbPRTransmitterBRefFaultEvent, dvbPRTransmitterBFaultMIPEvent, dvbPRTransmitterBMuteEvent, 
				dvbPRTransmitterBStuffingModeEvent }
			STATUS current
			DESCRIPTION 
				"Description. events"
			::= { groupsPR 2 }

		
		-- 1.3.6.1.4.1.19831.1.1.1.3.6.3
		obgectGroupPRobsolete OBJECT-GROUP
			OBJECTS { dvbPRResetFault, dvbPRResetFaultEnable, dvbPRResetFaultPriority }
			STATUS obsolete
			DESCRIPTION 
				"Description. Inactive objects"
			::= { groupsPR 3 }

		
		-- 1.3.6.1.4.1.19831.1.1.1.3.6.4
		eventGrpupPRobsolete NOTIFICATION-GROUP
			NOTIFICATIONS { dvbPRResetFaultEvent }
			STATUS obsolete
			DESCRIPTION 
				"Description. Inactive notifications"
			::= { groupsPR 4 }

		
		-- 1.3.6.1.4.1.19831.1.1.1.3.7
		compliancePR OBJECT IDENTIFIER ::= { dvbPassiveReserve 7 }

		
		-- 1.3.6.1.4.1.19831.1.1.1.3.7.1
		dvbPassiveReserveCompliance MODULE-COMPLIANCE
			STATUS current
			DESCRIPTION 
				"Compliance Statement"
			MODULE -- this module
				MANDATORY-GROUPS { obgectGroupPR, eventGrpupPR }
			::= { compliancePR 1 }

		
	
	END

--
-- IRT-DVBT-PASSIVERESERVE-MIB.my
--
